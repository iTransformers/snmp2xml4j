F5-BIGIP-SYSTEM-MIB DEFINITIONS ::= BEGIN
--================================================================
-- F5-BIGIP-SYSTEM-MIB 
--     A private enterprise MIB for F5  traffic management 
--     systems.
--     VERSION: 11.4.0
--================================================================

IMPORTS
    OBJECT-TYPE, NOTIFICATION-TYPE, MODULE-IDENTITY,
    Integer32, Opaque, enterprises, Counter32, Counter64, TimeTicks
        FROM SNMPv2-SMI

    Gauge 
        FROM RFC1155-SMI 

    TEXTUAL-CONVENTION, MacAddress 
        FROM SNMPv2-TC 

    CounterBasedGauge64 
        FROM HCNUM-TC 

    OBJECT-GROUP, MODULE-COMPLIANCE
        FROM SNMPv2-CONF

    InetAddress, InetAddressType, InetPortNumber
      FROM INET-ADDRESS-MIB

    bigipTrafficMgmt, bigipCompliances, bigipGroups, LongDisplayString
      FROM F5-BIGIP-COMMON-MIB;

--================================================================
bigipSystem MODULE-IDENTITY
    LAST-UPDATED "201305282141Z" -- Tue May 28 21:41:05 UTC 2013
    ORGANIZATION "F5 Networks, Inc."
    CONTACT-INFO
         "postal: F5 Networks, Inc. 
	 	  401 Elliott Ave. West 
                  Seattle, WA 98119
          phone:  (206) 272-5555
          email:  support@f5.com"

    DESCRIPTION
        "Top-level infrastructure of the F5 enterprise MIB tree." 
    ::= { bigipTrafficMgmt 1 }

--================================================================

--bigipSystem
sysGlobals               OBJECT IDENTIFIER ::= { bigipSystem 1 }
sysNetwork               OBJECT IDENTIFIER ::= { bigipSystem 2 }
sysPlatform              OBJECT IDENTIFIER ::= { bigipSystem 3 }
sysProduct               OBJECT IDENTIFIER ::= { bigipSystem 4 }
sysSubMemory             OBJECT IDENTIFIER ::= { bigipSystem 5 }
sysSystem                OBJECT IDENTIFIER ::= { bigipSystem 6 }
sysHostInfoStat          OBJECT IDENTIFIER ::= { bigipSystem 7 }
sysSystemStat            OBJECT IDENTIFIER ::= { bigipSystem 8 }
sysSoftware              OBJECT IDENTIFIER ::= { bigipSystem 9 }
sysClusters              OBJECT IDENTIFIER ::= { bigipSystem 10 }
sysModules               OBJECT IDENTIFIER ::= { bigipSystem 11 }
sysProcess               OBJECT IDENTIFIER ::= { bigipSystem 12 }
sysVCMP                  OBJECT IDENTIFIER ::= { bigipSystem 13 }
sysCM                    OBJECT IDENTIFIER ::= { bigipSystem 14 }


--sysNetwork
sysAdmin                 OBJECT IDENTIFIER ::= { sysNetwork 1 }
sysArpNdp                OBJECT IDENTIFIER ::= { sysNetwork 2}
sysDot1dBridge           OBJECT IDENTIFIER ::= { sysNetwork 3 }
sysInterfaces            OBJECT IDENTIFIER ::= { sysNetwork 4 }
sysL2                    OBJECT IDENTIFIER ::= { sysNetwork 5 }
sysPacketFilters         OBJECT IDENTIFIER ::= { sysNetwork 6 }
sysRoute                 OBJECT IDENTIFIER ::= { sysNetwork 7 }
sysSelfIps               OBJECT IDENTIFIER ::= { sysNetwork 8 }
sysSelfPorts             OBJECT IDENTIFIER ::= { sysNetwork 9 }
sysSpanningTree          OBJECT IDENTIFIER ::= { sysNetwork 10 }
sysTransmission          OBJECT IDENTIFIER ::= { sysNetwork 11 }
sysTrunks                OBJECT IDENTIFIER ::= { sysNetwork 12 }
sysVlans                 OBJECT IDENTIFIER ::= { sysNetwork 13 }
sysDevice                OBJECT IDENTIFIER ::= { sysNetwork 14 }
sysTunnels               OBJECT IDENTIFIER ::= { sysNetwork 15 }

--sysGlobals
sysGlobalAttrs           OBJECT IDENTIFIER ::= { sysGlobals 1 }
sysGlobalStats           OBJECT IDENTIFIER ::= { sysGlobals 2 }

--sysGlobalAttrs
sysGlobalAttr           OBJECT IDENTIFIER ::= { sysGlobalAttrs 1 }

--sysGlobalStats
sysGlobalStat           OBJECT IDENTIFIER ::= { sysGlobalStats 1 }
sysGlobalAuthStat       OBJECT IDENTIFIER ::= { sysGlobalStats 2 }
sysGlobalConnPoolStat   OBJECT IDENTIFIER ::= { sysGlobalStats 3 }
sysGlobalHttpStat       OBJECT IDENTIFIER ::= { sysGlobalStats 4 }
sysGlobalIcmpStat       OBJECT IDENTIFIER ::= { sysGlobalStats 5 }
sysGlobalIcmp6Stat      OBJECT IDENTIFIER ::= { sysGlobalStats 6 }
sysGlobalIpStat         OBJECT IDENTIFIER ::= { sysGlobalStats 7 }
sysGlobalIp6Stat        OBJECT IDENTIFIER ::= { sysGlobalStats 8 }
sysGlobalClientSslStat  OBJECT IDENTIFIER ::= { sysGlobalStats 9 }
sysGlobalServerSslStat  OBJECT IDENTIFIER ::= { sysGlobalStats 10 }
sysGlobalStreamStat     OBJECT IDENTIFIER ::= { sysGlobalStats 11 }
sysGlobalTcpStat        OBJECT IDENTIFIER ::= { sysGlobalStats 12 }
sysGlobalUdpStat        OBJECT IDENTIFIER ::= { sysGlobalStats 13 }
sysGlobalFastHttpStat   OBJECT IDENTIFIER ::= { sysGlobalStats 14 }
sysGlobalXmlStat        OBJECT IDENTIFIER ::= { sysGlobalStats 15 }
sysGlobalIiopStat       OBJECT IDENTIFIER ::= { sysGlobalStats 16 }
sysGlobalRtspStat       OBJECT IDENTIFIER ::= { sysGlobalStats 17 }
sysGlobalSctpStat       OBJECT IDENTIFIER ::= { sysGlobalStats 18 }
sysGlobalFastL4Stat     OBJECT IDENTIFIER ::= { sysGlobalStats 19 }
sysGlobalHost           OBJECT IDENTIFIER ::= { sysGlobalStats 20 }
sysGlobalTmmStat        OBJECT IDENTIFIER ::= { sysGlobalStats 21 }
sysGlobalHttpCompressionStat OBJECT IDENTIFIER ::= { sysGlobalStats 22 }
sysGlobalWebAccelerationStat OBJECT IDENTIFIER ::= { sysGlobalStats 23 }
sysGlobalDnsStat        OBJECT IDENTIFIER ::= { sysGlobalStats 24 }
sysGlobalLsnPoolStat    OBJECT IDENTIFIER ::= { sysGlobalStats 25 }

--sysAdmin
sysAdminIp               OBJECT IDENTIFIER ::= { sysAdmin 1 }

--sysDevice
sysSysDevice                      OBJECT IDENTIFIER ::= { sysDevice 1 }
sysUnicastAddr                    OBJECT IDENTIFIER ::= { sysDevice 2 }
sysSysDeviceActiveModules         OBJECT IDENTIFIER ::= { sysDevice 4 }
sysSysDeviceInactiveModules       OBJECT IDENTIFIER ::= { sysDevice 5 }
sysSysDeviceOptionalModules       OBJECT IDENTIFIER ::= { sysDevice 6 }
sysSysDeviceTimelimitedModules    OBJECT IDENTIFIER ::= { sysDevice 7 }

--sysPlatform
sysCpu                   OBJECT IDENTIFIER ::= { sysPlatform 1 }
sysChassis               OBJECT IDENTIFIER ::= { sysPlatform 2 }
sysGeneral               OBJECT IDENTIFIER ::= { sysPlatform 3 }
sysDeviceModelOIDs       OBJECT IDENTIFIER ::= { sysPlatform 4 }
sysPlatformInfo          OBJECT IDENTIFIER ::= { sysPlatform 5 }
sysCpuSensor             OBJECT IDENTIFIER ::= { sysPlatform 6 }

sysChassisFan            OBJECT IDENTIFIER ::= { sysChassis 1 }
sysChassisPowerSupply    OBJECT IDENTIFIER ::= { sysChassis 2 }
sysChassisTemp           OBJECT IDENTIFIER ::= { sysChassis 3 }

-- sysArpNdp
sysArpStaticEntry        OBJECT IDENTIFIER ::= { sysArpNdp 1 }

-- sysDot1dBridge
sysDot1dbaseStat         OBJECT IDENTIFIER ::= { sysDot1dBridge 1 }
sysDot1dbaseStatPort     OBJECT IDENTIFIER ::= { sysDot1dBridge 2 }

--sysInterfaces
sysInterface             OBJECT IDENTIFIER ::= { sysInterfaces 1 }
sysInterfaceMediaOptions OBJECT IDENTIFIER ::= { sysInterfaces 2 }
sysInterfaceId           OBJECT IDENTIFIER ::= { sysInterfaces 3 }
sysInterfaceStat         OBJECT IDENTIFIER ::= { sysInterfaces 4 }
sysIfxStat               OBJECT IDENTIFIER ::= { sysInterfaces 5 }
sysInterfaceMediaSfp OBJECT IDENTIFIER ::= { sysInterfaces 6 }

-- sysL2
sysL2Forward             OBJECT IDENTIFIER ::= { sysL2 1 }
sysL2ForwardStat         OBJECT IDENTIFIER ::= { sysL2 2 }
sysL2ForwardAttr         OBJECT IDENTIFIER ::= { sysL2 3 }

--sysPacketFilters     
sysPacketFilter          OBJECT IDENTIFIER ::= { sysPacketFilters 1 }
sysPacketFilterAddress   OBJECT IDENTIFIER ::= { sysPacketFilters 2 }
sysPacketFilterVlan      OBJECT IDENTIFIER ::= { sysPacketFilters 3 }
sysPacketFilterMac       OBJECT IDENTIFIER ::= { sysPacketFilters 4 }
sysPacketFilterStat      OBJECT IDENTIFIER ::= { sysPacketFilters 5 }

-- sysRoute
sysRouteMgmtEntry        OBJECT IDENTIFIER ::= { sysRoute 1 }
sysRouteStaticEntry      OBJECT IDENTIFIER ::= { sysRoute 2 }

--sysSelfIps
sysSelfIp                OBJECT IDENTIFIER ::= { sysSelfIps 1 }

--sysSelfPorts
sysSelfPort              OBJECT IDENTIFIER ::= { sysSelfPorts 1 }
sysSelfPortDefault       OBJECT IDENTIFIER ::= { sysSelfPorts 2 }

--sysSpanningTree
sysStp                   OBJECT IDENTIFIER ::= { sysSpanningTree 1 }
sysStpGlobals            OBJECT IDENTIFIER ::= { sysSpanningTree 2 }
sysStpInterfaceMbr       OBJECT IDENTIFIER ::= { sysSpanningTree 3 }
sysStpVlanMbr            OBJECT IDENTIFIER ::= { sysSpanningTree 4 }
sysStpBridgeStat         OBJECT IDENTIFIER ::= { sysSpanningTree 5 }
sysStpBridgeTreeStat     OBJECT IDENTIFIER ::= { sysSpanningTree 6 }
sysStpInterfaceStat      OBJECT IDENTIFIER ::= { sysSpanningTree 7 }
sysStpInterfaceTreeStat  OBJECT IDENTIFIER ::= { sysSpanningTree 8 }
sysStpGlobals2           OBJECT IDENTIFIER ::= { sysSpanningTree 9 }

--sysTransmission
sysDot3Stat              OBJECT IDENTIFIER ::= { sysTransmission 1 }

--sysTrunks
sysTrunk                 OBJECT IDENTIFIER ::= { sysTrunks 1 }
sysTrunkStat             OBJECT IDENTIFIER ::= { sysTrunks 2 }
sysTrunkCfgMember        OBJECT IDENTIFIER ::= { sysTrunks 3 }

--sysVlans
sysVlan                  OBJECT IDENTIFIER ::= { sysVlans 1 }
sysVlanMember            OBJECT IDENTIFIER ::= { sysVlans 2 }
sysVlanGroup             OBJECT IDENTIFIER ::= { sysVlans 3 }
sysVlanGroupMbr          OBJECT IDENTIFIER ::= { sysVlans 4 }
sysProxyExclusion        OBJECT IDENTIFIER ::= { sysVlans 5 }
sysVlanStat              OBJECT IDENTIFIER ::= { sysVlans 6 }
sysVlanxStat             OBJECT IDENTIFIER ::= { sysVlans 7 }

--sysTunnels
sysFecStat               OBJECT IDENTIFIER ::= { sysTunnels 1 }

--sysHostInfoStat
sysHostMemory            OBJECT IDENTIFIER ::= { sysHostInfoStat 1 }
sysHostCpu               OBJECT IDENTIFIER ::= { sysHostInfoStat 2 }
sysHostDisk              OBJECT IDENTIFIER ::= { sysHostInfoStat 3 }
sysMultiHost             OBJECT IDENTIFIER ::= { sysHostInfoStat 4 }
sysMultiHostCpu          OBJECT IDENTIFIER ::= { sysHostInfoStat 5 }
sysLogicalDisk           OBJECT IDENTIFIER ::= { sysHostInfoStat 6 }
sysPhysicalDisk          OBJECT IDENTIFIER ::= { sysHostInfoStat 7 }
sysDiskBay               OBJECT IDENTIFIER ::= { sysHostInfoStat 8 }
sysLogicalDiskMembers    OBJECT IDENTIFIER ::= { sysHostInfoStat 9 }

--sysSoftware
sysSoftwareVolume        OBJECT IDENTIFIER ::= { sysSoftware 1 }
sysSoftwareImage         OBJECT IDENTIFIER ::= { sysSoftware 2 }
sysSoftwareHotfix        OBJECT IDENTIFIER ::= { sysSoftware 3 }
sysSoftwareStatus        OBJECT IDENTIFIER ::= { sysSoftware 4 }

--sysSystemStat
sysPvaStat               OBJECT IDENTIFIER ::= { sysSystemStat 1 }
sysTmmStat               OBJECT IDENTIFIER ::= { sysSystemStat 2 }

--sysClusters
sysCluster               OBJECT IDENTIFIER ::= { sysClusters 1 }
sysClusterMbr            OBJECT IDENTIFIER ::= { sysClusters 2 }
sysChassisSlot           OBJECT IDENTIFIER ::= { sysClusters 3 }

--sysModules
sysModuleAllocation      OBJECT IDENTIFIER ::= { sysModules 1 }

--sysProcess
sysProcPidStat           OBJECT IDENTIFIER ::= { sysProcess 1 }

--sysVCMP
sysVcmp                  OBJECT IDENTIFIER ::= { sysVCMP 1 }
sysVcmpCpuCore           OBJECT IDENTIFIER ::= { sysVCMP 2 }
sysVcmpVlan              OBJECT IDENTIFIER ::= { sysVCMP 3 }
sysVcmpStat              OBJECT IDENTIFIER ::= { sysVCMP 4 }
sysVcmpAssignedSlots     OBJECT IDENTIFIER ::= { sysVCMP 5 }
sysVcmpAllowedSlots      OBJECT IDENTIFIER ::= { sysVCMP 6 }
sysVirtualDisk           OBJECT IDENTIFIER ::= { sysVCMP 7 }

--sysCM
sysCmSyncStatus          OBJECT IDENTIFIER ::= { sysCM 1 }
sysCmSyncStatusDetails   OBJECT IDENTIFIER ::= { sysCM 2 }
sysCmFailoverStatus      OBJECT IDENTIFIER ::= { sysCM 3 }
sysCmFailoverStatusDetails OBJECT IDENTIFIER ::= { sysCM 4 }
sysCmTrafficGroupStatus  OBJECT IDENTIFIER ::= { sysCM 5 }

bigip520                                OBJECT IDENTIFIER ::= { sysDeviceModelOIDs 1 }
bigip540                                OBJECT IDENTIFIER ::= { sysDeviceModelOIDs 2 }
bigip1000                               OBJECT IDENTIFIER ::= { sysDeviceModelOIDs 3 }
bigip1500                               OBJECT IDENTIFIER ::= { sysDeviceModelOIDs 4 }
bigip2400                               OBJECT IDENTIFIER ::= { sysDeviceModelOIDs 5 }
bigip3400                               OBJECT IDENTIFIER ::= { sysDeviceModelOIDs 6 }
bigip4100                               OBJECT IDENTIFIER ::= { sysDeviceModelOIDs 7 }
bigip5100                               OBJECT IDENTIFIER ::= { sysDeviceModelOIDs 8 }
bigip5110                               OBJECT IDENTIFIER ::= { sysDeviceModelOIDs 9 }
bigip6400                               OBJECT IDENTIFIER ::= { sysDeviceModelOIDs 10 }
bigip6800                               OBJECT IDENTIFIER ::= { sysDeviceModelOIDs 11 }
bigip8400                               OBJECT IDENTIFIER ::= { sysDeviceModelOIDs 12 }
bigip8800                               OBJECT IDENTIFIER ::= { sysDeviceModelOIDs 13 }
em3000                                  OBJECT IDENTIFIER ::= { sysDeviceModelOIDs 14 }
wj300                                   OBJECT IDENTIFIER ::= { sysDeviceModelOIDs 15 }
wj400                                   OBJECT IDENTIFIER ::= { sysDeviceModelOIDs 16 }
wj500                                   OBJECT IDENTIFIER ::= { sysDeviceModelOIDs 17 }
wj800                                   OBJECT IDENTIFIER ::= { sysDeviceModelOIDs 18 }
bigipPb200                              OBJECT IDENTIFIER ::= { sysDeviceModelOIDs 19 }
bigip1600                               OBJECT IDENTIFIER ::= { sysDeviceModelOIDs 20 }
bigip3600                               OBJECT IDENTIFIER ::= { sysDeviceModelOIDs 21 }
bigip6900                               OBJECT IDENTIFIER ::= { sysDeviceModelOIDs 22 }
bigip8900                               OBJECT IDENTIFIER ::= { sysDeviceModelOIDs 23 }
bigip3900                               OBJECT IDENTIFIER ::= { sysDeviceModelOIDs 24 }
bigip8950                               OBJECT IDENTIFIER ::= { sysDeviceModelOIDs 25 }
em4000                                  OBJECT IDENTIFIER ::= { sysDeviceModelOIDs 26 }
bigip11050                              OBJECT IDENTIFIER ::= { sysDeviceModelOIDs 27 }
em500                                   OBJECT IDENTIFIER ::= { sysDeviceModelOIDs 28 }

arx1000                                 OBJECT IDENTIFIER ::= { sysDeviceModelOIDs 29 }
arx2000                                 OBJECT IDENTIFIER ::= { sysDeviceModelOIDs 30 }
arx4000                                 OBJECT IDENTIFIER ::= { sysDeviceModelOIDs 31 }
arx500                                  OBJECT IDENTIFIER ::= { sysDeviceModelOIDs 32 }
bigip3410                               OBJECT IDENTIFIER ::= { sysDeviceModelOIDs 33 }
bigipPb100                              OBJECT IDENTIFIER ::= { sysDeviceModelOIDs 34 }
bigipPb100n                             OBJECT IDENTIFIER ::= { sysDeviceModelOIDs 35 }
sam4300                                 OBJECT IDENTIFIER ::= { sysDeviceModelOIDs 36 }
firepass1200                            OBJECT IDENTIFIER ::= { sysDeviceModelOIDs 37 }
firepass4100                            OBJECT IDENTIFIER ::= { sysDeviceModelOIDs 38 }
firepass4300                            OBJECT IDENTIFIER ::= { sysDeviceModelOIDs 39 }
swanWJ200                               OBJECT IDENTIFIER ::= { sysDeviceModelOIDs 40 }
TrafficShield4100                       OBJECT IDENTIFIER ::= { sysDeviceModelOIDs 41 }
wa4500                                  OBJECT IDENTIFIER ::= { sysDeviceModelOIDs 42 }
bigipVirtualEdition                     OBJECT IDENTIFIER ::= { sysDeviceModelOIDs 43 }

bigip11000                              OBJECT IDENTIFIER ::= { sysDeviceModelOIDs 44 }
bigip11050N                             OBJECT IDENTIFIER ::= { sysDeviceModelOIDs 45 }
bigipViprionB2100                       OBJECT IDENTIFIER ::= { sysDeviceModelOIDs 46 }
bigipViprionB4300                       OBJECT IDENTIFIER ::= { sysDeviceModelOIDs 47 }
bigipViprionC2400                       OBJECT IDENTIFIER ::= { sysDeviceModelOIDs 48 }
arx1500                                 OBJECT IDENTIFIER ::= { sysDeviceModelOIDs 49 }
arx2500                                 OBJECT IDENTIFIER ::= { sysDeviceModelOIDs 50 }
bigip11000F                             OBJECT IDENTIFIER ::= { sysDeviceModelOIDs 51 }
bigip11050F                             OBJECT IDENTIFIER ::= { sysDeviceModelOIDs 52 }
bigip6900F                              OBJECT IDENTIFIER ::= { sysDeviceModelOIDs 53 }
bigip6900N                              OBJECT IDENTIFIER ::= { sysDeviceModelOIDs 54 }
bigip6900S                              OBJECT IDENTIFIER ::= { sysDeviceModelOIDs 55 }
bigip8900F                              OBJECT IDENTIFIER ::= { sysDeviceModelOIDs 56 }
bigip8950S                              OBJECT IDENTIFIER ::= { sysDeviceModelOIDs 57 }
bigipPb200N                             OBJECT IDENTIFIER ::= { sysDeviceModelOIDs 58 }
bigip4000                               OBJECT IDENTIFIER ::= { sysDeviceModelOIDs 59 }
bigip10000                              OBJECT IDENTIFIER ::= { sysDeviceModelOIDs 60 }
bigip2000                               OBJECT IDENTIFIER ::= { sysDeviceModelOIDs 61 }
bigip5000                               OBJECT IDENTIFIER ::= { sysDeviceModelOIDs 62 }
bigip7000                               OBJECT IDENTIFIER ::= { sysDeviceModelOIDs 63 }
bigip800                                OBJECT IDENTIFIER ::= { sysDeviceModelOIDs 64 }
bigip10000F                             OBJECT IDENTIFIER ::= { sysDeviceModelOIDs 66 }
bigip10000S                             OBJECT IDENTIFIER ::= { sysDeviceModelOIDs 67 }

unknown                                 OBJECT IDENTIFIER ::= { sysDeviceModelOIDs 1000 }



--==================================================================
-- Global_attr
--==================================================================
sysAttrArpMaxEntries OBJECT-TYPE 
	SYNTAX Integer32
	MAX-ACCESS read-only
	STATUS current
	DESCRIPTION
		"The maximum number of dynamic entries which can be exist
		at one time."
	::= { sysGlobalAttr 1 } 

sysAttrArpAddReciprocal OBJECT-TYPE 
	SYNTAX INTEGER {
		disable(0),
		enable(1)
	}
	MAX-ACCESS read-only
	STATUS current
	DESCRIPTION
		"When enabled add the IP/MAC address of an ARP requester 
		into the ARP table. Enabling this field can allow a malicious 
		user on the local net to poison the ARP cache. Disabling 
		it reduces the performance of the system"
	::= { sysGlobalAttr 2 } 

sysAttrArpTimeout OBJECT-TYPE 
	SYNTAX Integer32
	MAX-ACCESS read-only
	STATUS current
	DESCRIPTION
		"Determine how long (in seconds) ARP entries are kept in
		the cache before being marked stale."
	::= { sysGlobalAttr 3 } 

sysAttrArpRetries OBJECT-TYPE 
	SYNTAX Integer32
	MAX-ACCESS read-only
	STATUS current
	DESCRIPTION
		"The maximum number of times to request an ARP before
		giving up and marking the IP address as unavailable."
	::= { sysGlobalAttr 4 } 

sysAttrBootQuiet OBJECT-TYPE 
	SYNTAX INTEGER {
		disable(0),
		enable(1)
	}
	MAX-ACCESS read-only
	STATUS current
	DESCRIPTION
		"The behavior of boot message display during a reboot of  
		the system. Enabling this suppresses the messages. 
		Disabling this displays messages."
	::= { sysGlobalAttr 5 } 

sysAttrConfigsyncState OBJECT-TYPE 
	SYNTAX LongDisplayString
	MAX-ACCESS read-only
	STATUS	 deprecated
	DESCRIPTION
		"Deprecated! Replaced by sysCmSyncStatus and sysCmSyncStatusDetails.
		 Enumerated state between peer systems.
		-1 - uninitialized or disabled config state
		 0 - Synchronized
		 1 - Local config modified, recommend configsync to peer
		 2 - Peer config modified, recommend configsync from peer
		 3 - Config modified on both systems, manual intervention required"
	::= { sysGlobalAttr 6 } 

sysAttrConnAdaptiveReaperHiwat OBJECT-TYPE 
	SYNTAX Integer32
	MAX-ACCESS read-only
	STATUS current
	DESCRIPTION
		"The high threshold for dynamic reaper, at which point no 
		 new connection will be allowed."
	::= { sysGlobalAttr 7 } 

sysAttrConnAdaptiveReaperLowat OBJECT-TYPE 
	SYNTAX Integer32
	MAX-ACCESS read-only
	STATUS current
	DESCRIPTION
		"The low threshold for dynamic reaper, at which point the 
		 reaper will kick in."
	::= { sysGlobalAttr 8 } 

sysAttrConnAutoLasthop OBJECT-TYPE 
	SYNTAX INTEGER {
		disable(0),
		enable(1)
	}
	MAX-ACCESS read-only
	STATUS current
	DESCRIPTION
		"The behavior of automatic last hop pools."
	::= { sysGlobalAttr 9 } 

sysAttrFailoverActiveMode OBJECT-TYPE 
	SYNTAX INTEGER {
		disable(0),
		enable(1)
	}
	MAX-ACCESS read-only
	STATUS	 deprecated
	DESCRIPTION
		"Deprecated! The redundant pair mode. Enabling is to use active-active mode. 
		By default this is disable, active-standby mode is used."
	::= { sysGlobalAttr 10 } 

sysAttrFailoverForceActive OBJECT-TYPE 
	SYNTAX INTEGER {
		disable(0),
		enable(1)
	}
	MAX-ACCESS read-only
	STATUS	 deprecated
	DESCRIPTION
		"Deprecated! The behavior of failover. Enabling makes failover daemon 
		always attempt to become the active unit."
	::= { sysGlobalAttr 11 } 

sysAttrFailoverForceStandby OBJECT-TYPE 
	SYNTAX INTEGER {
		disable(0),
		enable(1)
	}
	MAX-ACCESS read-only
	STATUS	 deprecated
	DESCRIPTION
		"Deprecated! The behavior of failover. Enabling makes failover daemon 
		go to standby whenever is senses its peer alive."
	::= { sysGlobalAttr 12 } 

sysAttrFailoverIsRedundant OBJECT-TYPE 
	SYNTAX INTEGER {
		false(0),
		true(1)
	}
	MAX-ACCESS read-only
	STATUS current
	DESCRIPTION
		"The redundant mode of the system."
	::= { sysGlobalAttr 13 } 

sysAttrFailoverMemoryRestartPercent OBJECT-TYPE 
	SYNTAX Integer32
	MAX-ACCESS read-only
	STATUS	 deprecated
	DESCRIPTION
		"Deprecated! Refer sysAttrConnAdaptiveReaperHiwat and sysAttrConnAdaptiveReaperLowat
		for memory threshold when TMM (Traffic Management Module) takes actions.   
		The percentage of memory usage that triggers reboot."
	::= { sysGlobalAttr 14 } 

sysAttrFailoverNetwork OBJECT-TYPE 
	SYNTAX INTEGER {
		disable(0),
		enable(1)
	}
	MAX-ACCESS read-only
	STATUS current
	DESCRIPTION
		"The  behavior of using the network as a backup to, or
		instead of, the serial line for failover if this value 
		is 1.  By default this feature is disabled."
	::= { sysGlobalAttr 15 } 

sysAttrFailoverStandbyLinkDownTime OBJECT-TYPE 
	SYNTAX Integer32
	MAX-ACCESS read-only
	STATUS current
	DESCRIPTION
		"How long the external link is held down when the unit 
		fails over and becomes standby. This is so an external 
		switch will update its L2 tables and use the newly active 
		unit's link. Each unit = 1/10 of a second. 
		Zero value = disable (ie. do not bring link down)."
	::= { sysGlobalAttr 16 } 

sysAttrFailoverSslhardware OBJECT-TYPE 
	SYNTAX INTEGER {
		disable(0),
		enable(1)
	}
	MAX-ACCESS read-only
	STATUS	 deprecated
	DESCRIPTION
		"Deprecated! This feature has been eliminated.
		Enables/disables the action prescribed by 
		sysAttrFailoverSslhardwareAction (failover or reboot)."
	::= { sysGlobalAttr 17 } 

sysAttrFailoverSslhardwareAction OBJECT-TYPE 
	SYNTAX INTEGER {
		failover(0),
		reboot(1)
	}
	MAX-ACCESS read-only
	STATUS	 deprecated
	DESCRIPTION
		"Deprecated! This feature has been eliminated.
		This is controlled by the sysAttrFailoverSslhardware.  
		If sysAttrFailoverSslhardware is enabled, the action 
		prescribed here will take place when SSL hardware fails."
	::= { sysGlobalAttr 18 } 

sysAttrFailoverUnitMask OBJECT-TYPE 
	SYNTAX Integer32
	MAX-ACCESS read-only
	STATUS	 deprecated
	DESCRIPTION
		"Deprecated! Refer to sysCmTrafficGroupStatus, sysCmFailoverStatus, and
		sysCmFailoverStatusDetails.
		This data indicates whether the machine is active or standby.
		The value for this data could be 0, 1, 2, or 3. 
		The values of 1 and 2 are only defined for an active-active installation. 
		If two boxes are both active, value for unit 1 will be 1 and value for unit 2 will be 2. 
		Otherwise, for active unit, this value is 3; for stand-by unit, this value is 0."
	::= { sysGlobalAttr 19 } 

sysAttrFailoverUnitId OBJECT-TYPE 
	SYNTAX Integer32
	MAX-ACCESS read-only
	STATUS	 deprecated
	DESCRIPTION
		"Deprecated! Refer to sysCmTrafficGroupStatus, sysCmFailoverStatus, and
		sysCmFailoverStatusDetails.
		The controller unique unit id, 1 or 2, in the event that 
		network communication is not possible with its peer."
	::= { sysGlobalAttr 20 } 

sysAttrModeMaint OBJECT-TYPE 
	SYNTAX INTEGER {
		disable(0),
		enable(1)
	}
	MAX-ACCESS read-only
	STATUS current
	DESCRIPTION
		"The state of system maintenance mode. 
		 disable - not in maintenance mode; 
		 enable  - maintenance mode."
	::= { sysGlobalAttr 21 } 

sysAttrPacketFilter OBJECT-TYPE 
	SYNTAX INTEGER {
		disabled(0),
		enabled(1)
	}
	MAX-ACCESS read-only
	STATUS current
	DESCRIPTION
		"This option globally enables or disables processing of all 
			packet filter options, including the rule list. The packet 
			filter is enabled by default."
	::= { sysGlobalAttr 22 } 

sysAttrPacketFilterAllowImportantIcmp OBJECT-TYPE 
	SYNTAX INTEGER {
		disabled(0),
		enabled(1)
	}
	MAX-ACCESS read-only
	STATUS current
	DESCRIPTION
		"This option causes the packet filter to automatically 
			accept a number of important ICMP types without requiring 
			the addition of a rule to handle them. Acceptance of ICMP 
			traffic by this option occurs prior to rule list evaluation, 
			making it impossible to override the behavior of this option 
			with a rule. The types of ICMP packets accepted by this 
			option include:
			UNREACH (3) - all types 
			SOURCEQUENCH (4) 
			REDIRECT (5) - all types 
			TIMEXCEED (11) - all types 
			This option is enabled by default."
	::= { sysGlobalAttr 23 } 

sysAttrPacketFilterEstablished OBJECT-TYPE 
	SYNTAX INTEGER {
		disabled(0),
		enabled(1)
	}
	MAX-ACCESS read-only
	STATUS current
	DESCRIPTION
		"The status of filter established feature. This option 
			 controls whether or not filter rules are applied to 
			 packets which are part of an existing, established 
			 connection or pseudo-connection. When this option is 
			 enabled, all ingress packets are subject to filter 
			 rules. When the option is disabled, filter rules are not 
			 applied to packets which are part of an existing 
			 connection. That is useful to prevent filtering of reply 
			 traffic. This option is disabled by default."
	::= { sysGlobalAttr 24 } 

sysAttrPacketFilterDefaultAction OBJECT-TYPE 
	SYNTAX INTEGER {
		accept(0),
		discard(1),
		reject(2)
	}
	MAX-ACCESS read-only
	STATUS current
	DESCRIPTION
		"The filter default action. This variable controls how to 
			 handle packets which did not match any rules. It can be 
			 either accept, discard or reject. The default value is 
			 accept."
	::= { sysGlobalAttr 25 } 

sysAttrPacketFilterSendIcmpErrors OBJECT-TYPE 
	SYNTAX INTEGER {
		disable(0),
		enable(1)
	}
	MAX-ACCESS read-only
	STATUS current
	DESCRIPTION
		"The feature to control the kind of errors to send for REJECT rules."
	::= { sysGlobalAttr 26 } 

sysAttrPvaAcceleration OBJECT-TYPE 
	SYNTAX INTEGER {
		none(0),
		partial(1),
		full(2)
	}
	MAX-ACCESS read-only
	STATUS current
	DESCRIPTION
		"The type of hardware acceleration desired."
	::= { sysGlobalAttr 27 } 

sysAttrVlanFDBTimeout OBJECT-TYPE 
	SYNTAX Integer32
	MAX-ACCESS read-only
	STATUS current
	DESCRIPTION
		"Controls how long before an entry expires in the L2 forwarding 
		database."
	::= { sysGlobalAttr 28 } 

sysAttrWatchdogState OBJECT-TYPE 
	SYNTAX INTEGER {
		disable(0),
		enable(1)
	}
	MAX-ACCESS read-only
	STATUS current
	DESCRIPTION
		"The state of watch dog feature - a hardware device that 
		 monitors the system for hardware failure. "
	::= { sysGlobalAttr 29 } 

--==================================================================
-- Global_stat
--==================================================================
sysStatResetStats OBJECT-TYPE 
	SYNTAX INTEGER
	MAX-ACCESS read-write
	STATUS current
	DESCRIPTION
		"The action to reset resetable statistics data in  sysGlobalStat. 
		 Setting this value to 1 will reset statistics data. 
		 Note, some statistics data may not be reset including data that are incremental counters."
	::= { sysGlobalStat 1 } 

sysStatClientPktsIn OBJECT-TYPE 
	SYNTAX Counter64
	MAX-ACCESS read-only
	STATUS current
	DESCRIPTION
		"The number of packets received by the system from client-side."
	::= { sysGlobalStat 2 } 

sysStatClientBytesIn OBJECT-TYPE 
	SYNTAX Counter64
	MAX-ACCESS read-only
	STATUS current
	DESCRIPTION
		"The number of bytes received by the system from client-side."
	::= { sysGlobalStat 3 } 

sysStatClientPktsOut OBJECT-TYPE 
	SYNTAX Counter64
	MAX-ACCESS read-only
	STATUS current
	DESCRIPTION
		"The number of packets sent to client-side from the system."
	::= { sysGlobalStat 4 } 

sysStatClientBytesOut OBJECT-TYPE 
	SYNTAX Counter64
	MAX-ACCESS read-only
	STATUS current
	DESCRIPTION
		"The number of bytes sent to client-side from the system."
	::= { sysGlobalStat 5 } 

sysStatClientMaxConns OBJECT-TYPE 
	SYNTAX Counter64
	MAX-ACCESS read-only
	STATUS current
	DESCRIPTION
		"The maximum connections from client-side to the system."
	::= { sysGlobalStat 6 } 

sysStatClientTotConns OBJECT-TYPE 
	SYNTAX Counter64
	MAX-ACCESS read-only
	STATUS current
	DESCRIPTION
		"The total connections from client-side to the system."
	::= { sysGlobalStat 7 } 

sysStatClientCurConns OBJECT-TYPE 
	SYNTAX CounterBasedGauge64
	MAX-ACCESS read-only
	STATUS current
	DESCRIPTION
		"The current connections from client-side to the system."
	::= { sysGlobalStat 8 } 

sysStatServerPktsIn OBJECT-TYPE 
	SYNTAX Counter64
	MAX-ACCESS read-only
	STATUS current
	DESCRIPTION
		"The number of packets received by the system from server-side."
	::= { sysGlobalStat 9 } 

sysStatServerBytesIn OBJECT-TYPE 
	SYNTAX Counter64
	MAX-ACCESS read-only
	STATUS current
	DESCRIPTION
		"The number of bytes received by the system from server-side."
	::= { sysGlobalStat 10 } 

sysStatServerPktsOut OBJECT-TYPE 
	SYNTAX Counter64
	MAX-ACCESS read-only
	STATUS current
	DESCRIPTION
		"The number of packets sent to server-side from the system."
	::= { sysGlobalStat 11 } 

sysStatServerBytesOut OBJECT-TYPE 
	SYNTAX Counter64
	MAX-ACCESS read-only
	STATUS current
	DESCRIPTION
		"The number of bytes sent to server-side from the system."
	::= { sysGlobalStat 12 } 

sysStatServerMaxConns OBJECT-TYPE 
	SYNTAX Counter64
	MAX-ACCESS read-only
	STATUS current
	DESCRIPTION
		"The maximum connections from server-side to the system."
	::= { sysGlobalStat 13 } 

sysStatServerTotConns OBJECT-TYPE 
	SYNTAX Counter64
	MAX-ACCESS read-only
	STATUS current
	DESCRIPTION
		"The total connections from server-side to the system."
	::= { sysGlobalStat 14 } 

sysStatServerCurConns OBJECT-TYPE 
	SYNTAX CounterBasedGauge64
	MAX-ACCESS read-only
	STATUS current
	DESCRIPTION
		"The current connections from server-side to the system."
	::= { sysGlobalStat 15 } 

sysStatPvaClientPktsIn OBJECT-TYPE 
	SYNTAX Counter64
	MAX-ACCESS read-only
	STATUS current
	DESCRIPTION
		"The number of hardware accelerated packets received 
		by the system from client-side."
	::= { sysGlobalStat 16 } 

sysStatPvaClientBytesIn OBJECT-TYPE 
	SYNTAX Counter64
	MAX-ACCESS read-only
	STATUS current
	DESCRIPTION
		"The number of hardware accelerated bytes received 
		by the system from client-side."
	::= { sysGlobalStat 17 } 

sysStatPvaClientPktsOut OBJECT-TYPE 
	SYNTAX Counter64
	MAX-ACCESS read-only
	STATUS current
	DESCRIPTION
		"The number of hardware accelerated packets sent to client-side from the system."
	::= { sysGlobalStat 18 } 

sysStatPvaClientBytesOut OBJECT-TYPE 
	SYNTAX Counter64
	MAX-ACCESS read-only
	STATUS current
	DESCRIPTION
		"The number of hardware accelerated bytes sent to client-side from the system."
	::= { sysGlobalStat 19 } 

sysStatPvaClientMaxConns OBJECT-TYPE 
	SYNTAX Counter64
	MAX-ACCESS read-only
	STATUS current
	DESCRIPTION
		"The maximum hardware accelerated connections from client-side to the system."
	::= { sysGlobalStat 20 } 

sysStatPvaClientTotConns OBJECT-TYPE 
	SYNTAX Counter64
	MAX-ACCESS read-only
	STATUS current
	DESCRIPTION
		"The total hardware accelerated connections from client-side to the system."
	::= { sysGlobalStat 21 } 

sysStatPvaClientCurConns OBJECT-TYPE 
	SYNTAX CounterBasedGauge64
	MAX-ACCESS read-only
	STATUS current
	DESCRIPTION
		"The current hardware accelerated connections from client-side to the system."
	::= { sysGlobalStat 22 } 

sysStatPvaServerPktsIn OBJECT-TYPE 
	SYNTAX Counter64
	MAX-ACCESS read-only
	STATUS current
	DESCRIPTION
		"The number of hardware accelerated packets received 
		by the system from server-side."
	::= { sysGlobalStat 23 } 

sysStatPvaServerBytesIn OBJECT-TYPE 
	SYNTAX Counter64
	MAX-ACCESS read-only
	STATUS current
	DESCRIPTION
		"The number of hardware accelerated bytes received 
		by the system from server-side."
	::= { sysGlobalStat 24 } 

sysStatPvaServerPktsOut OBJECT-TYPE 
	SYNTAX Counter64
	MAX-ACCESS read-only
	STATUS current
	DESCRIPTION
		"The number of hardware accelerated packets sent to server-side from the system."
	::= { sysGlobalStat 25 } 

sysStatPvaServerBytesOut OBJECT-TYPE 
	SYNTAX Counter64
	MAX-ACCESS read-only
	STATUS current
	DESCRIPTION
		"The number of hardware accelerated bytes sent to server-side from the system."
	::= { sysGlobalStat 26 } 

sysStatPvaServerMaxConns OBJECT-TYPE 
	SYNTAX Counter64
	MAX-ACCESS read-only
	STATUS current
	DESCRIPTION
		"The maximum hardware accelerated connections from server-side to the system."
	::= { sysGlobalStat 27 } 

sysStatPvaServerTotConns OBJECT-TYPE 
	SYNTAX Counter64
	MAX-ACCESS read-only
	STATUS current
	DESCRIPTION
		"The total hardware accelerated connections from server-side to the system."
	::= { sysGlobalStat 28 } 

sysStatPvaServerCurConns OBJECT-TYPE 
	SYNTAX CounterBasedGauge64
	MAX-ACCESS read-only
	STATUS current
	DESCRIPTION
		"The current hardware accelerated connections from server-side to the system."
	::= { sysGlobalStat 29 } 

sysStatTotPvaAssistConn OBJECT-TYPE 
	SYNTAX Counter64
	MAX-ACCESS read-only
	STATUS current
	DESCRIPTION
		"The total number of the partially hardware accelerated connections on the system."
	::= { sysGlobalStat 30 } 

sysStatCurrPvaAssistConn OBJECT-TYPE 
	SYNTAX CounterBasedGauge64
	MAX-ACCESS read-only
	STATUS current
	DESCRIPTION
		"The current number of the partially hardware accelerated connections on the system."
	::= { sysGlobalStat 31 } 

sysStatMaintenanceModeDeny OBJECT-TYPE 
	SYNTAX Counter64
	MAX-ACCESS read-only
	STATUS current
	DESCRIPTION
		"The connection requests rejected because the virtual
		server was in maintenance mode. "
	::= { sysGlobalStat 32 } 

sysStatMaxConnVirtualPathDeny OBJECT-TYPE 
	SYNTAX Counter64
	MAX-ACCESS read-only
	STATUS current
	DESCRIPTION
		"The connection requests rejected because they exceeded
		the connection limit for a virtual server (IP:port)."
	::= { sysGlobalStat 33 } 

sysStatVirtualServerNonSynDeny OBJECT-TYPE 
	SYNTAX Counter64
	MAX-ACCESS read-only
	STATUS current
	DESCRIPTION
		"The packets that are not connection requests and are 
		destined for a virtual server that has no connection 
		for the client address."
	::= { sysGlobalStat 34 } 

sysStatNoHandlerDeny OBJECT-TYPE 
	SYNTAX Counter64
	MAX-ACCESS read-only
	STATUS current
	DESCRIPTION
		"The incoming packets that could not be processed by a
		a virtual server, NAT, or SNAT."
	::= { sysGlobalStat 35 } 

sysStatLicenseDeny OBJECT-TYPE 
	SYNTAX Counter64
	MAX-ACCESS read-only
	STATUS current
	DESCRIPTION
		"The packets which were dropped due to exceeding licensing 
		limitations."
	::= { sysGlobalStat 36 } 

sysStatConnectionMemoryErrors OBJECT-TYPE 
	SYNTAX Counter64
	MAX-ACCESS read-only
	STATUS current
	DESCRIPTION
		"The errors of that connection could not be created because memory 
		was not available."
	::= { sysGlobalStat 37 } 

sysStatCpuCount OBJECT-TYPE 
	SYNTAX Counter64
	MAX-ACCESS read-only
	STATUS current
	DESCRIPTION
		"The number of CPUs on the system."
	::= { sysGlobalStat 38 } 

sysStatActiveCpuCount OBJECT-TYPE 
	SYNTAX Counter64
	MAX-ACCESS read-only
	STATUS current
	DESCRIPTION
		"The number of active CPUs on the system."
	::= { sysGlobalStat 39 } 

sysStatMultiProcessorMode OBJECT-TYPE 
	SYNTAX INTEGER {
		modeup(0),
		modesmp(1)
	}
	MAX-ACCESS read-only
	STATUS	 deprecated
	DESCRIPTION
		"Deprecated! Used to refer to the mode the system's processors were
			running in."
	::= { sysGlobalStat 40 } 

sysStatTmTotalCycles OBJECT-TYPE 
	SYNTAX Counter64
	MAX-ACCESS read-only
	STATUS current
	DESCRIPTION
		"Traffic management CPU usage. The total cycles spent in 
		traffic management."
	::= { sysGlobalStat 41 } 

sysStatTmIdleCycles OBJECT-TYPE 
	SYNTAX Counter64
	MAX-ACCESS read-only
	STATUS current
	DESCRIPTION
		"Traffic management CPU usage. The cycles spent polling with no 
		traffic."
	::= { sysGlobalStat 42 } 

sysStatTmSleepCycles OBJECT-TYPE 
	SYNTAX Counter64
	MAX-ACCESS read-only
	STATUS current
	DESCRIPTION
		"Traffic management CPU usage. The cycles yielded."
	::= { sysGlobalStat 43 } 

sysStatMemoryTotal OBJECT-TYPE 
	SYNTAX CounterBasedGauge64
	MAX-ACCESS read-only
	STATUS current
	DESCRIPTION
		"The total memory available in bytes for TMM (Traffic Management Module)."
	::= { sysGlobalStat 44 } 

sysStatMemoryUsed OBJECT-TYPE 
	SYNTAX CounterBasedGauge64
	MAX-ACCESS read-only
	STATUS current
	DESCRIPTION
		"The memory in use in bytes for TMM (Traffic Management Module)."
	::= { sysGlobalStat 45 } 

sysStatDroppedPackets OBJECT-TYPE 
	SYNTAX Counter64
	MAX-ACCESS read-only
	STATUS current
	DESCRIPTION
		"The total dropped packets."
	::= { sysGlobalStat 46 } 

sysStatIncomingPacketErrors OBJECT-TYPE 
	SYNTAX Counter64
	MAX-ACCESS read-only
	STATUS current
	DESCRIPTION
		"The total incoming packet errors for the system."
	::= { sysGlobalStat 47 } 

sysStatOutgoingPacketErrors OBJECT-TYPE 
	SYNTAX Counter64
	MAX-ACCESS read-only
	STATUS current
	DESCRIPTION
		"The total outgoing packet errors for the system."
	::= { sysGlobalStat 48 } 

sysStatAuthTotSessions OBJECT-TYPE 
	SYNTAX Counter64
	MAX-ACCESS read-only
	STATUS current
	DESCRIPTION
		"The total number of concurrent auth sessions on the system."
	::= { sysGlobalStat 49 } 

sysStatAuthCurSessions OBJECT-TYPE 
	SYNTAX CounterBasedGauge64
	MAX-ACCESS read-only
	STATUS current
	DESCRIPTION
		"The current number of concurrent auth sessions on the system."
	::= { sysGlobalStat 50 } 

sysStatAuthMaxSessions OBJECT-TYPE 
	SYNTAX Counter64
	MAX-ACCESS read-only
	STATUS current
	DESCRIPTION
		"The maximum number of concurrent auth sessions on the system."
	::= { sysGlobalStat 51 } 

sysStatAuthSuccessResults OBJECT-TYPE 
	SYNTAX Counter64
	MAX-ACCESS read-only
	STATUS current
	DESCRIPTION
		"The total number of auth success results (That is when a 
		successful authorization has completed all of the required 
		auth services.) on the system."
	::= { sysGlobalStat 52 } 

sysStatAuthFailureResults OBJECT-TYPE 
	SYNTAX Counter64
	MAX-ACCESS read-only
	STATUS current
	DESCRIPTION
		"The total number of auth failure results (That is when an 
		unsuccessful authorization operation has completed.) on the system."
	::= { sysGlobalStat 53 } 

sysStatAuthWantcredentialResults OBJECT-TYPE 
	SYNTAX Counter64
	MAX-ACCESS read-only
	STATUS current
	DESCRIPTION
		"The total number of auth wantcredential results (That is when 
		an authorization operation needs an additional credential.) on the system."
	::= { sysGlobalStat 54 } 

sysStatAuthErrorResults OBJECT-TYPE 
	SYNTAX Counter64
	MAX-ACCESS read-only
	STATUS current
	DESCRIPTION
		"The total number of auth error results (That is when an error 
		occurred during authorization has occurred.) on the system."
	::= { sysGlobalStat 55 } 

sysStatHttpRequests OBJECT-TYPE 
	SYNTAX Counter64
	MAX-ACCESS read-only
	STATUS current
	DESCRIPTION
		"The total number of HTTP requests to the system."
	::= { sysGlobalStat 56 } 

sysStatHardSyncookieGen OBJECT-TYPE 
	SYNTAX Counter64
	MAX-ACCESS read-only
	STATUS current
	DESCRIPTION
		"The number of hardware SYN cookies are generated on the system."
	::= { sysGlobalStat 57 } 

sysStatHardSyncookieDet OBJECT-TYPE 
	SYNTAX Counter64
	MAX-ACCESS read-only
	STATUS current
	DESCRIPTION
		"The number of hardware SYN cookies are detected on the system."
	::= { sysGlobalStat 58 } 

sysStatClientPktsIn5s OBJECT-TYPE 
	SYNTAX CounterBasedGauge64
	MAX-ACCESS read-only
	STATUS current
	DESCRIPTION
		"The average number of packets received by the system from client-side in the last five seconds."
	::= { sysGlobalStat 59 } 

sysStatClientBytesIn5s OBJECT-TYPE 
	SYNTAX CounterBasedGauge64
	MAX-ACCESS read-only
	STATUS current
	DESCRIPTION
		"The average number of bytes received by the system from client-side in the last five seconds."
	::= { sysGlobalStat 60 } 

sysStatClientPktsOut5s OBJECT-TYPE 
	SYNTAX CounterBasedGauge64
	MAX-ACCESS read-only
	STATUS current
	DESCRIPTION
		"The average number of packets sent to client-side from the system in the last five seconds."
	::= { sysGlobalStat 61 } 

sysStatClientBytesOut5s OBJECT-TYPE 
	SYNTAX CounterBasedGauge64
	MAX-ACCESS read-only
	STATUS current
	DESCRIPTION
		"The average number of bytes sent to client-side from the system in the last five seconds."
	::= { sysGlobalStat 62 } 

sysStatClientMaxConns5s OBJECT-TYPE 
	SYNTAX CounterBasedGauge64
	MAX-ACCESS read-only
	STATUS current
	DESCRIPTION
		"The average maximum connections from client-side to the system in the last five seconds."
	::= { sysGlobalStat 63 } 

sysStatClientTotConns5s OBJECT-TYPE 
	SYNTAX CounterBasedGauge64
	MAX-ACCESS read-only
	STATUS current
	DESCRIPTION
		"The average total connections from client-side to the system in the last five seconds."
	::= { sysGlobalStat 64 } 

sysStatClientCurConns5s OBJECT-TYPE 
	SYNTAX CounterBasedGauge64
	MAX-ACCESS read-only
	STATUS current
	DESCRIPTION
		"The average current connections from client-side to the system in the last five seconds."
	::= { sysGlobalStat 65 } 

sysStatServerPktsIn5s OBJECT-TYPE 
	SYNTAX CounterBasedGauge64
	MAX-ACCESS read-only
	STATUS current
	DESCRIPTION
		"The average number of packets received by the system from server-side in the last five seconds."
	::= { sysGlobalStat 66 } 

sysStatServerBytesIn5s OBJECT-TYPE 
	SYNTAX CounterBasedGauge64
	MAX-ACCESS read-only
	STATUS current
	DESCRIPTION
		"The average number of bytes received by the system from server-side in the last five seconds."
	::= { sysGlobalStat 67 } 

sysStatServerPktsOut5s OBJECT-TYPE 
	SYNTAX CounterBasedGauge64
	MAX-ACCESS read-only
	STATUS current
	DESCRIPTION
		"The average number of packets sent to server-side from the system in the last five seconds."
	::= { sysGlobalStat 68 } 

sysStatServerBytesOut5s OBJECT-TYPE 
	SYNTAX CounterBasedGauge64
	MAX-ACCESS read-only
	STATUS current
	DESCRIPTION
		"The average number of bytes sent to server-side from the system in the last five seconds."
	::= { sysGlobalStat 69 } 

sysStatServerMaxConns5s OBJECT-TYPE 
	SYNTAX CounterBasedGauge64
	MAX-ACCESS read-only
	STATUS current
	DESCRIPTION
		"The average maximum connections from server-side to the system in the last five seconds."
	::= { sysGlobalStat 70 } 

sysStatServerTotConns5s OBJECT-TYPE 
	SYNTAX CounterBasedGauge64
	MAX-ACCESS read-only
	STATUS current
	DESCRIPTION
		"The average total connections from server-side to the system in the last five seconds."
	::= { sysGlobalStat 71 } 

sysStatServerCurConns5s OBJECT-TYPE 
	SYNTAX CounterBasedGauge64
	MAX-ACCESS read-only
	STATUS current
	DESCRIPTION
		"The average current connections from server-side to the system in the last five seconds."
	::= { sysGlobalStat 72 } 

sysStatClientPktsIn1m OBJECT-TYPE 
	SYNTAX CounterBasedGauge64
	MAX-ACCESS read-only
	STATUS current
	DESCRIPTION
		"The average number of packets received by the system from client-side in the last one minute."
	::= { sysGlobalStat 73 } 

sysStatClientBytesIn1m OBJECT-TYPE 
	SYNTAX CounterBasedGauge64
	MAX-ACCESS read-only
	STATUS current
	DESCRIPTION
		"The average number of bytes received by the system from client-side in the last one minute."
	::= { sysGlobalStat 74 } 

sysStatClientPktsOut1m OBJECT-TYPE 
	SYNTAX CounterBasedGauge64
	MAX-ACCESS read-only
	STATUS current
	DESCRIPTION
		"The average number of packets sent to client-side from the system in the last one minute."
	::= { sysGlobalStat 75 } 

sysStatClientBytesOut1m OBJECT-TYPE 
	SYNTAX CounterBasedGauge64
	MAX-ACCESS read-only
	STATUS current
	DESCRIPTION
		"The average number of bytes sent to client-side from the system in the last one minute."
	::= { sysGlobalStat 76 } 

sysStatClientMaxConns1m OBJECT-TYPE 
	SYNTAX CounterBasedGauge64
	MAX-ACCESS read-only
	STATUS current
	DESCRIPTION
		"The average maximum connections from client-side to the system in the last one minute."
	::= { sysGlobalStat 77 } 

sysStatClientTotConns1m OBJECT-TYPE 
	SYNTAX CounterBasedGauge64
	MAX-ACCESS read-only
	STATUS current
	DESCRIPTION
		"The average total connections from client-side to the system in the last one minute."
	::= { sysGlobalStat 78 } 

sysStatClientCurConns1m OBJECT-TYPE 
	SYNTAX CounterBasedGauge64
	MAX-ACCESS read-only
	STATUS current
	DESCRIPTION
		"The average current connections from client-side to the system in the last one minute."
	::= { sysGlobalStat 79 } 

sysStatServerPktsIn1m OBJECT-TYPE 
	SYNTAX CounterBasedGauge64
	MAX-ACCESS read-only
	STATUS current
	DESCRIPTION
		"The average number of packets received by the system from server-side in the last one minute."
	::= { sysGlobalStat 80 } 

sysStatServerBytesIn1m OBJECT-TYPE 
	SYNTAX CounterBasedGauge64
	MAX-ACCESS read-only
	STATUS current
	DESCRIPTION
		"The average number of bytes received by the system from server-side in the last one minute."
	::= { sysGlobalStat 81 } 

sysStatServerPktsOut1m OBJECT-TYPE 
	SYNTAX CounterBasedGauge64
	MAX-ACCESS read-only
	STATUS current
	DESCRIPTION
		"The average number of packets sent to server-side from the system in the last one minute."
	::= { sysGlobalStat 82 } 

sysStatServerBytesOut1m OBJECT-TYPE 
	SYNTAX CounterBasedGauge64
	MAX-ACCESS read-only
	STATUS current
	DESCRIPTION
		"The average number of bytes sent to server-side from the system in the last one minute."
	::= { sysGlobalStat 83 } 

sysStatServerMaxConns1m OBJECT-TYPE 
	SYNTAX CounterBasedGauge64
	MAX-ACCESS read-only
	STATUS current
	DESCRIPTION
		"The average maximum connections from server-side to the system in the last one minute."
	::= { sysGlobalStat 84 } 

sysStatServerTotConns1m OBJECT-TYPE 
	SYNTAX CounterBasedGauge64
	MAX-ACCESS read-only
	STATUS current
	DESCRIPTION
		"The average total connections from server-side to the system in the last one minute."
	::= { sysGlobalStat 85 } 

sysStatServerCurConns1m OBJECT-TYPE 
	SYNTAX CounterBasedGauge64
	MAX-ACCESS read-only
	STATUS current
	DESCRIPTION
		"The average current connections from server-side to the system in the last one minute."
	::= { sysGlobalStat 86 } 

sysStatClientPktsIn5m OBJECT-TYPE 
	SYNTAX CounterBasedGauge64
	MAX-ACCESS read-only
	STATUS current
	DESCRIPTION
		"The average average number of packets received by the system from client-side in the last five minutes."
	::= { sysGlobalStat 87 } 

sysStatClientBytesIn5m OBJECT-TYPE 
	SYNTAX CounterBasedGauge64
	MAX-ACCESS read-only
	STATUS current
	DESCRIPTION
		"The average number of bytes received by the system from client-side in the last five minutes."
	::= { sysGlobalStat 88 } 

sysStatClientPktsOut5m OBJECT-TYPE 
	SYNTAX CounterBasedGauge64
	MAX-ACCESS read-only
	STATUS current
	DESCRIPTION
		"The average number of packets sent to client-side from the system in the last five minutes."
	::= { sysGlobalStat 89 } 

sysStatClientBytesOut5m OBJECT-TYPE 
	SYNTAX CounterBasedGauge64
	MAX-ACCESS read-only
	STATUS current
	DESCRIPTION
		"The average number of bytes sent to client-side from the system in the last five minutes."
	::= { sysGlobalStat 90 } 

sysStatClientMaxConns5m OBJECT-TYPE 
	SYNTAX CounterBasedGauge64
	MAX-ACCESS read-only
	STATUS current
	DESCRIPTION
		"The average maximum connections from client-side to the system in the last five minutes."
	::= { sysGlobalStat 91 } 

sysStatClientTotConns5m OBJECT-TYPE 
	SYNTAX CounterBasedGauge64
	MAX-ACCESS read-only
	STATUS current
	DESCRIPTION
		"The average total connections from client-side to the system in the last five minutes."
	::= { sysGlobalStat 92 } 

sysStatClientCurConns5m OBJECT-TYPE 
	SYNTAX CounterBasedGauge64
	MAX-ACCESS read-only
	STATUS current
	DESCRIPTION
		"The average current connections from client-side to the system in the last five minutes."
	::= { sysGlobalStat 93 } 

sysStatServerPktsIn5m OBJECT-TYPE 
	SYNTAX CounterBasedGauge64
	MAX-ACCESS read-only
	STATUS current
	DESCRIPTION
		"The average number of packets received by the system from server-side in the last five minutes."
	::= { sysGlobalStat 94 } 

sysStatServerBytesIn5m OBJECT-TYPE 
	SYNTAX CounterBasedGauge64
	MAX-ACCESS read-only
	STATUS current
	DESCRIPTION
		"The average number of bytes received by the system from server-side in the last five minutes."
	::= { sysGlobalStat 95 } 

sysStatServerPktsOut5m OBJECT-TYPE 
	SYNTAX CounterBasedGauge64
	MAX-ACCESS read-only
	STATUS current
	DESCRIPTION
		"The average number of packets sent to server-side from the system in the last five minutes."
	::= { sysGlobalStat 96 } 

sysStatServerBytesOut5m OBJECT-TYPE 
	SYNTAX CounterBasedGauge64
	MAX-ACCESS read-only
	STATUS current
	DESCRIPTION
		"The average number of bytes sent to server-side from the system in the last five minutes."
	::= { sysGlobalStat 97 } 

sysStatServerMaxConns5m OBJECT-TYPE 
	SYNTAX CounterBasedGauge64
	MAX-ACCESS read-only
	STATUS current
	DESCRIPTION
		"The average maximum connections from server-side to the system in the last five minutes."
	::= { sysGlobalStat 98 } 

sysStatServerTotConns5m OBJECT-TYPE 
	SYNTAX CounterBasedGauge64
	MAX-ACCESS read-only
	STATUS current
	DESCRIPTION
		"The average total connections from server-side to the system in the last five minutes."
	::= { sysGlobalStat 99 } 

sysStatServerCurConns5m OBJECT-TYPE 
	SYNTAX CounterBasedGauge64
	MAX-ACCESS read-only
	STATUS current
	DESCRIPTION
		"The average current connections from server-side to the system in the last five minutes."
	::= { sysGlobalStat 100 } 

sysStatPvaClientPktsIn5s OBJECT-TYPE 
	SYNTAX CounterBasedGauge64
	MAX-ACCESS read-only
	STATUS current
	DESCRIPTION
		"The average number of hardware accelerated packets received 
		by the system from client-side in the last five seconds."
	::= { sysGlobalStat 101 } 

sysStatPvaClientBytesIn5s OBJECT-TYPE 
	SYNTAX CounterBasedGauge64
	MAX-ACCESS read-only
	STATUS current
	DESCRIPTION
		"The average number of hardware accelerated bytes received 
		by the system from client-side in the last five seconds."
	::= { sysGlobalStat 102 } 

sysStatPvaClientPktsOut5s OBJECT-TYPE 
	SYNTAX CounterBasedGauge64
	MAX-ACCESS read-only
	STATUS current
	DESCRIPTION
		"The average number of hardware accelerated packets sent to client-side from the system in the last five seconds."
	::= { sysGlobalStat 103 } 

sysStatPvaClientBytesOut5s OBJECT-TYPE 
	SYNTAX CounterBasedGauge64
	MAX-ACCESS read-only
	STATUS current
	DESCRIPTION
		"The average  number of hardware accelerated bytes sent to client-side from the system in the last five seconds."
	::= { sysGlobalStat 104 } 

sysStatPvaClientMaxConns5s OBJECT-TYPE 
	SYNTAX CounterBasedGauge64
	MAX-ACCESS read-only
	STATUS current
	DESCRIPTION
		"The average maximum hardware accelerated connections from client-side to the system in the last five seconds."
	::= { sysGlobalStat 105 } 

sysStatPvaClientTotConns5s OBJECT-TYPE 
	SYNTAX CounterBasedGauge64
	MAX-ACCESS read-only
	STATUS current
	DESCRIPTION
		"The average total hardware accelerated connections from client-side to the system in the last five seconds."
	::= { sysGlobalStat 106 } 

sysStatPvaClientCurConns5s OBJECT-TYPE 
	SYNTAX CounterBasedGauge64
	MAX-ACCESS read-only
	STATUS current
	DESCRIPTION
		"The average current hardware accelerated connections from client-side to the system in the last five seconds."
	::= { sysGlobalStat 107 } 

sysStatPvaServerPktsIn5s OBJECT-TYPE 
	SYNTAX CounterBasedGauge64
	MAX-ACCESS read-only
	STATUS current
	DESCRIPTION
		"The average number of hardware accelerated packets received 
		by the system from server-side in the last five seconds."
	::= { sysGlobalStat 108 } 

sysStatPvaServerBytesIn5s OBJECT-TYPE 
	SYNTAX CounterBasedGauge64
	MAX-ACCESS read-only
	STATUS current
	DESCRIPTION
		"The average number of hardware accelerated bytes received 
		by the system from server-side in the last five seconds."
	::= { sysGlobalStat 109 } 

sysStatPvaServerPktsOut5s OBJECT-TYPE 
	SYNTAX CounterBasedGauge64
	MAX-ACCESS read-only
	STATUS current
	DESCRIPTION
		"The average number of hardware accelerated packets sent to server-side from the system in the last five seconds."
	::= { sysGlobalStat 110 } 

sysStatPvaServerBytesOut5s OBJECT-TYPE 
	SYNTAX CounterBasedGauge64
	MAX-ACCESS read-only
	STATUS current
	DESCRIPTION
		"The average number of hardware accelerated bytes sent to server-side from the system in the last five seconds."
	::= { sysGlobalStat 111 } 

sysStatPvaServerMaxConns5s OBJECT-TYPE 
	SYNTAX CounterBasedGauge64
	MAX-ACCESS read-only
	STATUS current
	DESCRIPTION
		"The average maximum hardware accelerated connections from server-side to the system in the last five seconds."
	::= { sysGlobalStat 112 } 

sysStatPvaServerTotConns5s OBJECT-TYPE 
	SYNTAX CounterBasedGauge64
	MAX-ACCESS read-only
	STATUS current
	DESCRIPTION
		"The average total hardware accelerated connections from server-side to the system in the last five seconds."
	::= { sysGlobalStat 113 } 

sysStatPvaServerCurConns5s OBJECT-TYPE 
	SYNTAX CounterBasedGauge64
	MAX-ACCESS read-only
	STATUS current
	DESCRIPTION
		"The average current hardware accelerated connections from server-side to the system in the last five seconds."
	::= { sysGlobalStat 114 } 

sysStatPvaClientPktsIn1m OBJECT-TYPE 
	SYNTAX CounterBasedGauge64
	MAX-ACCESS read-only
	STATUS current
	DESCRIPTION
		"The average number of hardware accelerated packets received 
		by the system from client-side in the last five seconds."
	::= { sysGlobalStat 115 } 

sysStatPvaClientBytesIn1m OBJECT-TYPE 
	SYNTAX CounterBasedGauge64
	MAX-ACCESS read-only
	STATUS current
	DESCRIPTION
		"The average number of hardware accelerated bytes received
		by the system from client-side in the last one minute."
	::= { sysGlobalStat 116 } 

sysStatPvaClientPktsOut1m OBJECT-TYPE 
	SYNTAX CounterBasedGauge64
	MAX-ACCESS read-only
	STATUS current
	DESCRIPTION
		"The average number of hardware accelerated packets sent to client-side from the system in the last one minute."
	::= { sysGlobalStat 117 } 

sysStatPvaClientBytesOut1m OBJECT-TYPE 
	SYNTAX CounterBasedGauge64
	MAX-ACCESS read-only
	STATUS current
	DESCRIPTION
		"The average  number of hardware accelerated bytes sent to client-side from the system in the last one minute."
	::= { sysGlobalStat 118 } 

sysStatPvaClientMaxConns1m OBJECT-TYPE 
	SYNTAX CounterBasedGauge64
	MAX-ACCESS read-only
	STATUS current
	DESCRIPTION
		"The average maximum hardware accelerated connections from client-side to the system in the last one minute."
	::= { sysGlobalStat 119 } 

sysStatPvaClientTotConns1m OBJECT-TYPE 
	SYNTAX CounterBasedGauge64
	MAX-ACCESS read-only
	STATUS current
	DESCRIPTION
		"The average total hardware accelerated connections from client-side to the system in the last one minute."
	::= { sysGlobalStat 120 } 

sysStatPvaClientCurConns1m OBJECT-TYPE 
	SYNTAX CounterBasedGauge64
	MAX-ACCESS read-only
	STATUS current
	DESCRIPTION
		"The average current hardware accelerated connections from client-side to the system in the last one minute."
	::= { sysGlobalStat 121 } 

sysStatPvaServerPktsIn1m OBJECT-TYPE 
	SYNTAX CounterBasedGauge64
	MAX-ACCESS read-only
	STATUS current
	DESCRIPTION
		"The average number of hardware accelerated packets received 
		by the system from server-side in the last one minute."
	::= { sysGlobalStat 122 } 

sysStatPvaServerBytesIn1m OBJECT-TYPE 
	SYNTAX CounterBasedGauge64
	MAX-ACCESS read-only
	STATUS current
	DESCRIPTION
		"The average number of hardware accelerated bytes received 
		by the system from server-side in the last one minute."
	::= { sysGlobalStat 123 } 

sysStatPvaServerPktsOut1m OBJECT-TYPE 
	SYNTAX CounterBasedGauge64
	MAX-ACCESS read-only
	STATUS current
	DESCRIPTION
		"The average number of hardware accelerated packets sent to server-side from the system in the last one minute."
	::= { sysGlobalStat 124 } 

sysStatPvaServerBytesOut1m OBJECT-TYPE 
	SYNTAX CounterBasedGauge64
	MAX-ACCESS read-only
	STATUS current
	DESCRIPTION
		"The average number of hardware accelerated bytes sent to server-side from the system in the last one minute."
	::= { sysGlobalStat 125 } 

sysStatPvaServerMaxConns1m OBJECT-TYPE 
	SYNTAX CounterBasedGauge64
	MAX-ACCESS read-only
	STATUS current
	DESCRIPTION
		"The average maximum hardware accelerated connections from server-side to the system in the last one minute."
	::= { sysGlobalStat 126 } 

sysStatPvaServerTotConns1m OBJECT-TYPE 
	SYNTAX CounterBasedGauge64
	MAX-ACCESS read-only
	STATUS current
	DESCRIPTION
		"The average total hardware accelerated connections from server-side to the system in the last one minute."
	::= { sysGlobalStat 127 } 

sysStatPvaServerCurConns1m OBJECT-TYPE 
	SYNTAX CounterBasedGauge64
	MAX-ACCESS read-only
	STATUS current
	DESCRIPTION
		"The average current hardware accelerated connections from server-side to the system in the last one minute."
	::= { sysGlobalStat 128 } 

sysStatPvaClientPktsIn5m OBJECT-TYPE 
	SYNTAX CounterBasedGauge64
	MAX-ACCESS read-only
	STATUS current
	DESCRIPTION
		"The average number of hardware accelerated packets received 
		by the system from client-side in the last five minutes."
	::= { sysGlobalStat 129 } 

sysStatPvaClientBytesIn5m OBJECT-TYPE 
	SYNTAX CounterBasedGauge64
	MAX-ACCESS read-only
	STATUS current
	DESCRIPTION
		"The average number of hardware accelerated bytes received 
		by the system from client-side in the last five minutes."
	::= { sysGlobalStat 130 } 

sysStatPvaClientPktsOut5m OBJECT-TYPE 
	SYNTAX CounterBasedGauge64
	MAX-ACCESS read-only
	STATUS current
	DESCRIPTION
		"The average number of hardware accelerated packets sent to client-side from the system in the last five minutes."
	::= { sysGlobalStat 131 } 

sysStatPvaClientBytesOut5m OBJECT-TYPE 
	SYNTAX CounterBasedGauge64
	MAX-ACCESS read-only
	STATUS current
	DESCRIPTION
		"The average  number of hardware accelerated bytes sent to client-side from the system in the last five minutes."
	::= { sysGlobalStat 132 } 

sysStatPvaClientMaxConns5m OBJECT-TYPE 
	SYNTAX CounterBasedGauge64
	MAX-ACCESS read-only
	STATUS current
	DESCRIPTION
		"The average maximum hardware accelerated connections from client-side to the system in the last five minutes."
	::= { sysGlobalStat 133 } 

sysStatPvaClientTotConns5m OBJECT-TYPE 
	SYNTAX CounterBasedGauge64
	MAX-ACCESS read-only
	STATUS current
	DESCRIPTION
		"The average total hardware accelerated connections from client-side to the system in the last five minutes."
	::= { sysGlobalStat 134 } 

sysStatPvaClientCurConns5m OBJECT-TYPE 
	SYNTAX CounterBasedGauge64
	MAX-ACCESS read-only
	STATUS current
	DESCRIPTION
		"The average current hardware accelerated connections from client-side to the system in the last five minutes."
	::= { sysGlobalStat 135 } 

sysStatPvaServerPktsIn5m OBJECT-TYPE 
	SYNTAX CounterBasedGauge64
	MAX-ACCESS read-only
	STATUS current
	DESCRIPTION
		"The average number of hardware accelerated packets received 
		by the system from server-side in the last five minutes."
	::= { sysGlobalStat 136 } 

sysStatPvaServerBytesIn5m OBJECT-TYPE 
	SYNTAX CounterBasedGauge64
	MAX-ACCESS read-only
	STATUS current
	DESCRIPTION
		"The average number of hardware accelerated bytes received 
		by the system from server-side in the last five minutes."
	::= { sysGlobalStat 137 } 

sysStatPvaServerPktsOut5m OBJECT-TYPE 
	SYNTAX CounterBasedGauge64
	MAX-ACCESS read-only
	STATUS current
	DESCRIPTION
		"The average number of hardware accelerated packets sent to server-side from the system in the last five minutes."
	::= { sysGlobalStat 138 } 

sysStatPvaServerBytesOut5m OBJECT-TYPE 
	SYNTAX CounterBasedGauge64
	MAX-ACCESS read-only
	STATUS current
	DESCRIPTION
		"The average number of hardware accelerated bytes sent to server-side from the system in the last five minutes."
	::= { sysGlobalStat 139 } 

sysStatPvaServerMaxConns5m OBJECT-TYPE 
	SYNTAX CounterBasedGauge64
	MAX-ACCESS read-only
	STATUS current
	DESCRIPTION
		"The average maximum hardware accelerated connections from server-side to the system in the last five minutes."
	::= { sysGlobalStat 140 } 

sysStatPvaServerTotConns5m OBJECT-TYPE 
	SYNTAX CounterBasedGauge64
	MAX-ACCESS read-only
	STATUS current
	DESCRIPTION
		"The average total hardware accelerated connections from server-side to the system in the last five minutes."
	::= { sysGlobalStat 141 } 

sysStatPvaServerCurConns5m OBJECT-TYPE 
	SYNTAX CounterBasedGauge64
	MAX-ACCESS read-only
	STATUS current
	DESCRIPTION
		"The average current hardware accelerated connections from server-side to the system in the last five minutes."
	::= { sysGlobalStat 142 } 

sysStatMemoryTotalKb OBJECT-TYPE 
	SYNTAX CounterBasedGauge64
	MAX-ACCESS read-only
	STATUS current
	DESCRIPTION
		"The total memory available in Kilobytes for TMM (Traffic Management Module)."
	::= { sysGlobalStat 143 } 

sysStatMemoryUsedKb OBJECT-TYPE 
	SYNTAX CounterBasedGauge64
	MAX-ACCESS read-only
	STATUS current
	DESCRIPTION
		"The memory in use in Kilobytes for TMM (Traffic Management Module)."
	::= { sysGlobalStat 144 } 

--==================================================================
-- Global_auth_stat
--==================================================================
sysAuthStatResetStats OBJECT-TYPE 
	SYNTAX INTEGER
	MAX-ACCESS read-write
	STATUS current
	DESCRIPTION
		"The action to reset resetable statistics data in  sysGlobalAuthStat. 
		 Setting this value to 1 will reset statistics data. 
		 Note, some statistics data may not be reset including data that are incremental counters."
	::= { sysGlobalAuthStat 1 } 

sysAuthStatTotSessions OBJECT-TYPE 
	SYNTAX Counter64
	MAX-ACCESS read-only
	STATUS current
	DESCRIPTION
		"The total number of concurrent auth sessions."
	::= { sysGlobalAuthStat 2 } 

sysAuthStatCurSessions OBJECT-TYPE 
	SYNTAX CounterBasedGauge64
	MAX-ACCESS read-only
	STATUS current
	DESCRIPTION
		"The current number of concurrent auth sessions."
	::= { sysGlobalAuthStat 3 } 

sysAuthStatMaxSessions OBJECT-TYPE 
	SYNTAX Counter64
	MAX-ACCESS read-only
	STATUS current
	DESCRIPTION
		"The maximum number of concurrent auth sessions"
	::= { sysGlobalAuthStat 4 } 

sysAuthStatSuccessResults OBJECT-TYPE 
	SYNTAX Counter64
	MAX-ACCESS read-only
	STATUS current
	DESCRIPTION
		"The total number of auth success results (That is when a 
		successful authorization has completed all of the required 
		auth services.)."
	::= { sysGlobalAuthStat 5 } 

sysAuthStatFailureResults OBJECT-TYPE 
	SYNTAX Counter64
	MAX-ACCESS read-only
	STATUS current
	DESCRIPTION
		"The total number of auth failure results (That is when an 
		unsuccessful authorization operation has completed.)."
	::= { sysGlobalAuthStat 6 } 

sysAuthStatWantcredentialResults OBJECT-TYPE 
	SYNTAX Counter64
	MAX-ACCESS read-only
	STATUS current
	DESCRIPTION
		"The total number of auth wantcredential results (That is when 
		an authorization operation needs an additional credential.)"
	::= { sysGlobalAuthStat 7 } 

sysAuthStatErrorResults OBJECT-TYPE 
	SYNTAX Counter64
	MAX-ACCESS read-only
	STATUS current
	DESCRIPTION
		"The total number of auth error results (That is when an error 
		occurred during authorization has occurred.)."
	::= { sysGlobalAuthStat 8 } 

--==================================================================
-- Global_connpool_stat
--==================================================================
sysConnPoolStatResetStats OBJECT-TYPE 
	SYNTAX INTEGER
	MAX-ACCESS read-write
	STATUS current
	DESCRIPTION
		"The action to reset resetable statistics data in  sysGlobalConnPoolStat. 
		 Setting this value to 1 will reset statistics data. 
		 Note, some statistics data may not be reset including data that are incremental counters."
	::= { sysGlobalConnPoolStat 1 } 

sysConnPoolStatCurSize OBJECT-TYPE 
	SYNTAX Integer32
	MAX-ACCESS read-only
	STATUS current
	DESCRIPTION
		"The number of currently idle connections in pools on the system."
	::= { sysGlobalConnPoolStat 2 } 

sysConnPoolStatMaxSize OBJECT-TYPE 
	SYNTAX Integer32
	MAX-ACCESS read-only
	STATUS current
	DESCRIPTION
		"The number of idle connections in pools on the system."
	::= { sysGlobalConnPoolStat 3 } 

sysConnPoolStatReuses OBJECT-TYPE 
	SYNTAX Integer32
	MAX-ACCESS read-only
	STATUS current
	DESCRIPTION
		"The number of times a connection was reused from pools on the system."
	::= { sysGlobalConnPoolStat 4 } 

sysConnPoolStatConnects OBJECT-TYPE 
	SYNTAX Integer32
	MAX-ACCESS read-only
	STATUS current
	DESCRIPTION
		"The number of times a new connection was initiated in pools on the system."
	::= { sysGlobalConnPoolStat 5 } 

--==================================================================
-- Global_http_stat
--==================================================================
sysHttpStatResetStats OBJECT-TYPE 
	SYNTAX INTEGER
	MAX-ACCESS read-write
	STATUS current
	DESCRIPTION
		"The action to reset resetable statistics data in  sysGlobalHttpStat. 
		 Setting this value to 1 will reset statistics data. 
		 Note, some statistics data may not be reset including data that are incremental counters."
	::= { sysGlobalHttpStat 1 } 

sysHttpStatCookiePersistInserts OBJECT-TYPE 
	SYNTAX Counter64
	MAX-ACCESS read-only
	STATUS current
	DESCRIPTION
		"The number of successful attempts to insert HTTP headers 
		 for cookie persistence (set-cookie header insertions)."
	::= { sysGlobalHttpStat 2 } 

sysHttpStatResp2xxCnt OBJECT-TYPE 
	SYNTAX Counter64
	MAX-ACCESS read-only
	STATUS current
	DESCRIPTION
		"The number of server-side responses in range of 200 to 206 
		 (successful responses)"
	::= { sysGlobalHttpStat 3 } 

sysHttpStatResp3xxCnt OBJECT-TYPE 
	SYNTAX Counter64
	MAX-ACCESS read-only
	STATUS current
	DESCRIPTION
		"The number of server-side responses in range of 300 to 307 
		 (redirection responses)."
	::= { sysGlobalHttpStat 4 } 

sysHttpStatResp4xxCnt OBJECT-TYPE 
	SYNTAX Counter64
	MAX-ACCESS read-only
	STATUS current
	DESCRIPTION
		"The number of server-side responses in range of 400 to 417  
		 (client errors)."
	::= { sysGlobalHttpStat 5 } 

sysHttpStatResp5xxCnt OBJECT-TYPE 
	SYNTAX Counter64
	MAX-ACCESS read-only
	STATUS current
	DESCRIPTION
		"The number of server-side responses in range of 500 to 505 
		 (server errors)."
	::= { sysGlobalHttpStat 6 } 

sysHttpStatNumberReqs OBJECT-TYPE 
	SYNTAX Counter64
	MAX-ACCESS read-only
	STATUS current
	DESCRIPTION
		"The total number of HTTP requests."
	::= { sysGlobalHttpStat 7 } 

sysHttpStatGetReqs OBJECT-TYPE 
	SYNTAX Counter64
	MAX-ACCESS read-only
	STATUS current
	DESCRIPTION
		"The total number of HTTP get requests."
	::= { sysGlobalHttpStat 8 } 

sysHttpStatPostReqs OBJECT-TYPE 
	SYNTAX Counter64
	MAX-ACCESS read-only
	STATUS current
	DESCRIPTION
		"The total number of HTTP post requests."
	::= { sysGlobalHttpStat 9 } 

sysHttpStatV9Reqs OBJECT-TYPE 
	SYNTAX Counter64
	MAX-ACCESS read-only
	STATUS current
	DESCRIPTION
		"The total number of version 9 requests."
	::= { sysGlobalHttpStat 10 } 

sysHttpStatV10Reqs OBJECT-TYPE 
	SYNTAX Counter64
	MAX-ACCESS read-only
	STATUS current
	DESCRIPTION
		"The total number of version 10 requests."
	::= { sysGlobalHttpStat 11 } 

sysHttpStatV11Reqs OBJECT-TYPE 
	SYNTAX Counter64
	MAX-ACCESS read-only
	STATUS current
	DESCRIPTION
		"The total number of version 11 requests."
	::= { sysGlobalHttpStat 12 } 

sysHttpStatV9Resp OBJECT-TYPE 
	SYNTAX Counter64
	MAX-ACCESS read-only
	STATUS current
	DESCRIPTION
		"The total number of version 9 responses."
	::= { sysGlobalHttpStat 13 } 

sysHttpStatV10Resp OBJECT-TYPE 
	SYNTAX Counter64
	MAX-ACCESS read-only
	STATUS current
	DESCRIPTION
		"The total number of version 10 responses."
	::= { sysGlobalHttpStat 14 } 

sysHttpStatV11Resp OBJECT-TYPE 
	SYNTAX Counter64
	MAX-ACCESS read-only
	STATUS current
	DESCRIPTION
		"The total number of version 11 responses."
	::= { sysGlobalHttpStat 15 } 

sysHttpStatMaxKeepaliveReq OBJECT-TYPE 
	SYNTAX Counter64
	MAX-ACCESS read-only
	STATUS current
	DESCRIPTION
		"The maximum number of requests made in a connection."
	::= { sysGlobalHttpStat 16 } 

sysHttpStatRespBucket1k OBJECT-TYPE 
	SYNTAX Counter64
	MAX-ACCESS read-only
	STATUS current
	DESCRIPTION
		"The number of responses under 1k."
	::= { sysGlobalHttpStat 17 } 

sysHttpStatRespBucket4k OBJECT-TYPE 
	SYNTAX Counter64
	MAX-ACCESS read-only
	STATUS current
	DESCRIPTION
		"The number of responses under 1 - 4k."
	::= { sysGlobalHttpStat 18 } 

sysHttpStatRespBucket16k OBJECT-TYPE 
	SYNTAX Counter64
	MAX-ACCESS read-only
	STATUS current
	DESCRIPTION
		"The number of responses under 4 - 16k."
	::= { sysGlobalHttpStat 19 } 

sysHttpStatRespBucket32k OBJECT-TYPE 
	SYNTAX Counter64
	MAX-ACCESS read-only
	STATUS current
	DESCRIPTION
		"The number of responses under 16 - 32k."
	::= { sysGlobalHttpStat 20 } 

sysHttpStatPrecompressBytes OBJECT-TYPE 
	SYNTAX Counter64
	MAX-ACCESS read-only
	STATUS	 deprecated
	DESCRIPTION
		"Deprecated!  The number of response bytes before compression has taken place."
	::= { sysGlobalHttpStat 21 } 

sysHttpStatPostcompressBytes OBJECT-TYPE 
	SYNTAX Counter64
	MAX-ACCESS read-only
	STATUS	 deprecated
	DESCRIPTION
		"Deprecated!  The number of response bytes after compression has taken place."
	::= { sysGlobalHttpStat 22 } 

sysHttpStatNullCompressBytes OBJECT-TYPE 
	SYNTAX Counter64
	MAX-ACCESS read-only
	STATUS	 deprecated
	DESCRIPTION
		"Deprecated!  The number of bytes subjected to NULL compression (for license enforcement)."
	::= { sysGlobalHttpStat 23 } 

sysHttpStatHtmlPrecompressBytes OBJECT-TYPE 
	SYNTAX Counter64
	MAX-ACCESS read-only
	STATUS	 deprecated
	DESCRIPTION
		"Deprecated!  The number of precompressed bytes for the MIME-Types: HTML."
	::= { sysGlobalHttpStat 24 } 

sysHttpStatHtmlPostcompressBytes OBJECT-TYPE 
	SYNTAX Counter64
	MAX-ACCESS read-only
	STATUS	 deprecated
	DESCRIPTION
		"Deprecated!  The number of postcompressed bytes for the MIME-Types: HTML."
	::= { sysGlobalHttpStat 25 } 

sysHttpStatCssPrecompressBytes OBJECT-TYPE 
	SYNTAX Counter64
	MAX-ACCESS read-only
	STATUS	 deprecated
	DESCRIPTION
		"Deprecated!  The number of precompressed bytes for the MIME-Types: CSS."
	::= { sysGlobalHttpStat 26 } 

sysHttpStatCssPostcompressBytes OBJECT-TYPE 
	SYNTAX Counter64
	MAX-ACCESS read-only
	STATUS	 deprecated
	DESCRIPTION
		"Deprecated!  The number of postcompressed bytes for the MIME-Types: CSS."
	::= { sysGlobalHttpStat 27 } 

sysHttpStatJsPrecompressBytes OBJECT-TYPE 
	SYNTAX Counter64
	MAX-ACCESS read-only
	STATUS	 deprecated
	DESCRIPTION
		"Deprecated!  The number of precompressed bytes for the MIME-Types: Javascript."
	::= { sysGlobalHttpStat 28 } 

sysHttpStatJsPostcompressBytes OBJECT-TYPE 
	SYNTAX Counter64
	MAX-ACCESS read-only
	STATUS	 deprecated
	DESCRIPTION
		"Deprecated!  The number of postcompressed bytes for the MIME-Types: Javascript."
	::= { sysGlobalHttpStat 29 } 

sysHttpStatXmlPrecompressBytes OBJECT-TYPE 
	SYNTAX Counter64
	MAX-ACCESS read-only
	STATUS	 deprecated
	DESCRIPTION
		"Deprecated!  The number of precompressed bytes for the MIME-Types: XML."
	::= { sysGlobalHttpStat 30 } 

sysHttpStatXmlPostcompressBytes OBJECT-TYPE 
	SYNTAX Counter64
	MAX-ACCESS read-only
	STATUS	 deprecated
	DESCRIPTION
		"Deprecated!  The number of postcompressed bytes for the MIME-Types: XML."
	::= { sysGlobalHttpStat 31 } 

sysHttpStatSgmlPrecompressBytes OBJECT-TYPE 
	SYNTAX Counter64
	MAX-ACCESS read-only
	STATUS	 deprecated
	DESCRIPTION
		"Deprecated!  The number of precompressed bytes for the MIME-Types: SGML."
	::= { sysGlobalHttpStat 32 } 

sysHttpStatSgmlPostcompressBytes OBJECT-TYPE 
	SYNTAX Counter64
	MAX-ACCESS read-only
	STATUS	 deprecated
	DESCRIPTION
		"Deprecated!  The number of postcompressed bytes for the MIME-Types: SGML."
	::= { sysGlobalHttpStat 33 } 

sysHttpStatPlainPrecompressBytes OBJECT-TYPE 
	SYNTAX Counter64
	MAX-ACCESS read-only
	STATUS	 deprecated
	DESCRIPTION
		"Deprecated!  The number of precompressed bytes for the MIME-Types: Plain."
	::= { sysGlobalHttpStat 34 } 

sysHttpStatPlainPostcompressBytes OBJECT-TYPE 
	SYNTAX Counter64
	MAX-ACCESS read-only
	STATUS	 deprecated
	DESCRIPTION
		"Deprecated!  The number of postcompressed bytes for the MIME-Types: Plain."
	::= { sysGlobalHttpStat 35 } 

sysHttpStatOctetPrecompressBytes OBJECT-TYPE 
	SYNTAX Counter64
	MAX-ACCESS read-only
	STATUS	 deprecated
	DESCRIPTION
		"Deprecated!  The number of precompressed bytes for the MIME-Types: Octet stream."
	::= { sysGlobalHttpStat 36 } 

sysHttpStatOctetPostcompressBytes OBJECT-TYPE 
	SYNTAX Counter64
	MAX-ACCESS read-only
	STATUS	 deprecated
	DESCRIPTION
		"Deprecated!  The number of postcompressed bytes for the MIME-Types: Octet stream."
	::= { sysGlobalHttpStat 37 } 

sysHttpStatImagePrecompressBytes OBJECT-TYPE 
	SYNTAX Counter64
	MAX-ACCESS read-only
	STATUS	 deprecated
	DESCRIPTION
		"Deprecated!  The number of precompressed bytes for the MIME-Types: Images."
	::= { sysGlobalHttpStat 38 } 

sysHttpStatImagePostcompressBytes OBJECT-TYPE 
	SYNTAX Counter64
	MAX-ACCESS read-only
	STATUS	 deprecated
	DESCRIPTION
		"Deprecated!  The number of postcompressed bytes for the MIME-Types: Images."
	::= { sysGlobalHttpStat 39 } 

sysHttpStatVideoPrecompressBytes OBJECT-TYPE 
	SYNTAX Counter64
	MAX-ACCESS read-only
	STATUS	 deprecated
	DESCRIPTION
		"Deprecated!  The number of precompressed bytes for the MIME-Types: Video files."
	::= { sysGlobalHttpStat 40 } 

sysHttpStatVideoPostcompressBytes OBJECT-TYPE 
	SYNTAX Counter64
	MAX-ACCESS read-only
	STATUS	 deprecated
	DESCRIPTION
		"Deprecated!  The number of postcompressed bytes for the MIME-Types: Video files."
	::= { sysGlobalHttpStat 41 } 

sysHttpStatAudioPrecompressBytes OBJECT-TYPE 
	SYNTAX Counter64
	MAX-ACCESS read-only
	STATUS	 deprecated
	DESCRIPTION
		"Deprecated!  The number of precompressed bytes for the MIME-Types: Audio files."
	::= { sysGlobalHttpStat 42 } 

sysHttpStatAudioPostcompressBytes OBJECT-TYPE 
	SYNTAX Counter64
	MAX-ACCESS read-only
	STATUS	 deprecated
	DESCRIPTION
		"Deprecated!  The number of postcompressed bytes for the MIME-Types: Audio files."
	::= { sysGlobalHttpStat 43 } 

sysHttpStatOtherPrecompressBytes OBJECT-TYPE 
	SYNTAX Counter64
	MAX-ACCESS read-only
	STATUS	 deprecated
	DESCRIPTION
		"Deprecated!  The number of precompressed bytes for the MIME-Types: other than 
		HTML, CSS, Javascript, XML, SGML, Plain, Images, Video files, 
		Audio files."
	::= { sysGlobalHttpStat 44 } 

sysHttpStatOtherPostcompressBytes OBJECT-TYPE 
	SYNTAX Counter64
	MAX-ACCESS read-only
	STATUS	 deprecated
	DESCRIPTION
		"Deprecated!  The number of postcompressed bytes for the MIME-Types: other than 
		HTML, CSS, Javascript, XML, SGML, Plain, Images, Video files, 
		Audio files."
	::= { sysGlobalHttpStat 45 } 

sysHttpStatRamcacheHits OBJECT-TYPE 
	SYNTAX Counter64
	MAX-ACCESS read-only
	STATUS	 deprecated
	DESCRIPTION
		"Deprecated!  The number of RAM cache hits."
	::= { sysGlobalHttpStat 46 } 

sysHttpStatRamcacheMisses OBJECT-TYPE 
	SYNTAX Counter64
	MAX-ACCESS read-only
	STATUS	 deprecated
	DESCRIPTION
		"Deprecated!  The number of RAM cache misses, excluding un-cacheable data."
	::= { sysGlobalHttpStat 47 } 

sysHttpStatRamcacheMissesAll OBJECT-TYPE 
	SYNTAX Counter64
	MAX-ACCESS read-only
	STATUS	 deprecated
	DESCRIPTION
		"Deprecated!  The total number of RAM cache misses."
	::= { sysGlobalHttpStat 48 } 

sysHttpStatRamcacheHitBytes OBJECT-TYPE 
	SYNTAX Counter64
	MAX-ACCESS read-only
	STATUS	 deprecated
	DESCRIPTION
		"Deprecated!  The number of RAM cache hits in bytes."
	::= { sysGlobalHttpStat 49 } 

sysHttpStatRamcacheMissBytes OBJECT-TYPE 
	SYNTAX Counter64
	MAX-ACCESS read-only
	STATUS	 deprecated
	DESCRIPTION
		"Deprecated!  The number of RAM cache misses in bytes, excluding un-cacheable data."
	::= { sysGlobalHttpStat 50 } 

sysHttpStatRamcacheMissBytesAll OBJECT-TYPE 
	SYNTAX Counter64
	MAX-ACCESS read-only
	STATUS	 deprecated
	DESCRIPTION
		"Deprecated!  The total number of RAM cache misses in bytes."
	::= { sysGlobalHttpStat 51 } 

sysHttpStatRamcacheSize OBJECT-TYPE 
	SYNTAX Counter64
	MAX-ACCESS read-only
	STATUS	 deprecated
	DESCRIPTION
		"Deprecated!  The Ram cache current size."
	::= { sysGlobalHttpStat 52 } 

sysHttpStatRamcacheCount OBJECT-TYPE 
	SYNTAX Counter64
	MAX-ACCESS read-only
	STATUS	 deprecated
	DESCRIPTION
		"Deprecated!  The number of items stored in Ram cache."
	::= { sysGlobalHttpStat 53 } 

sysHttpStatRamcacheEvictions OBJECT-TYPE 
	SYNTAX Counter64
	MAX-ACCESS read-only
	STATUS	 deprecated
	DESCRIPTION
		"Deprecated!  The number of Ram cache evictions."
	::= { sysGlobalHttpStat 54 } 

sysHttpStatRespBucket64k OBJECT-TYPE 
	SYNTAX Counter64
	MAX-ACCESS read-only
	STATUS	 deprecated
	DESCRIPTION
		"Deprecated! Please use the larger buckets."
	::= { sysGlobalHttpStat 55 } 

--==================================================================
-- Icmp_stat
--==================================================================
sysIcmpStatResetStats OBJECT-TYPE 
	SYNTAX INTEGER
	MAX-ACCESS read-write
	STATUS current
	DESCRIPTION
		"The action to reset resetable statistics data in  sysGlobalIcmpStat. 
		 Setting this value to 1 will reset statistics data. 
		 Note, some statistics data may not be reset including data that are incremental counters."
	::= { sysGlobalIcmpStat 1 } 

sysIcmpStatTx OBJECT-TYPE 
	SYNTAX Counter64
	MAX-ACCESS read-only
	STATUS current
	DESCRIPTION
		"The total number of ICMP messages which this entity attempted 
		to send."
	::= { sysGlobalIcmpStat 2 } 

sysIcmpStatRx OBJECT-TYPE 
	SYNTAX Counter64
	MAX-ACCESS read-only
	STATUS current
	DESCRIPTION
		"The total number of ICMP messages which the entity received."
	::= { sysGlobalIcmpStat 3 } 

sysIcmpStatForward OBJECT-TYPE 
	SYNTAX Counter64
	MAX-ACCESS read-only
	STATUS current
	DESCRIPTION
		"The number of ICMP messages which the entity forwarded."
	::= { sysGlobalIcmpStat 4 } 

sysIcmpStatDrop OBJECT-TYPE 
	SYNTAX Counter64
	MAX-ACCESS read-only
	STATUS current
	DESCRIPTION
		"The number of ICMP messages which the entity dropped."
	::= { sysGlobalIcmpStat 5 } 

sysIcmpStatErrCksum OBJECT-TYPE 
	SYNTAX Counter64
	MAX-ACCESS read-only
	STATUS current
	DESCRIPTION
		"The number of ICMP messages which the entity received but 
		determined as having ICMP-specific errors, bad ICMP checksums."
	::= { sysGlobalIcmpStat 6 } 

sysIcmpStatErrLen OBJECT-TYPE 
	SYNTAX Counter64
	MAX-ACCESS read-only
	STATUS current
	DESCRIPTION
		"The number of ICMP messages which the entity received but 
			determined as having ICMP-specific errors, bad ICMP bad length."
	::= { sysGlobalIcmpStat 7 } 

sysIcmpStatErrMem OBJECT-TYPE 
	SYNTAX Counter64
	MAX-ACCESS read-only
	STATUS current
	DESCRIPTION
		"The number of memory allocation errors in the process."
	::= { sysGlobalIcmpStat 8 } 

sysIcmpStatErrRtx OBJECT-TYPE 
	SYNTAX Counter64
	MAX-ACCESS read-only
	STATUS current
	DESCRIPTION
		"The number of routing errors."
	::= { sysGlobalIcmpStat 9 } 

sysIcmpStatErrProto OBJECT-TYPE 
	SYNTAX Counter64
	MAX-ACCESS read-only
	STATUS current
	DESCRIPTION
		"The number of ICMP messages which the entity received but
		determined as having protocol errors."
	::= { sysGlobalIcmpStat 10 } 

sysIcmpStatErrOpt OBJECT-TYPE 
	SYNTAX Counter64
	MAX-ACCESS read-only
	STATUS current
	DESCRIPTION
		"The number of errors in options."
	::= { sysGlobalIcmpStat 11 } 

sysIcmpStatErr OBJECT-TYPE 
	SYNTAX Counter64
	MAX-ACCESS read-only
	STATUS current
	DESCRIPTION
		"The number of other not specified errors."
	::= { sysGlobalIcmpStat 12 } 

--==================================================================
-- Icmp6_stat
--==================================================================
sysIcmp6StatResetStats OBJECT-TYPE 
	SYNTAX INTEGER
	MAX-ACCESS read-write
	STATUS current
	DESCRIPTION
		"The action to reset resetable statistics data in  sysGlobalIcmp6Stat. 
		 Setting this value to 1 will reset statistics data. 
		 Note, some statistics data may not be reset including data that are incremental counters."
	::= { sysGlobalIcmp6Stat 1 } 

sysIcmp6StatTx OBJECT-TYPE 
	SYNTAX Counter64
	MAX-ACCESS read-only
	STATUS current
	DESCRIPTION
		"The total number of ICMP messages which this entity attempted 
		to send."
	::= { sysGlobalIcmp6Stat 2 } 

sysIcmp6StatRx OBJECT-TYPE 
	SYNTAX Counter64
	MAX-ACCESS read-only
	STATUS current
	DESCRIPTION
		"The total number of ICMP messages which the entity received."
	::= { sysGlobalIcmp6Stat 3 } 

sysIcmp6StatForward OBJECT-TYPE 
	SYNTAX Counter64
	MAX-ACCESS read-only
	STATUS current
	DESCRIPTION
		"The number of ICMP messages which the entity forwarded."
	::= { sysGlobalIcmp6Stat 4 } 

sysIcmp6StatDrop OBJECT-TYPE 
	SYNTAX Counter64
	MAX-ACCESS read-only
	STATUS current
	DESCRIPTION
		"The number of ICMP messages which the entity dropped."
	::= { sysGlobalIcmp6Stat 5 } 

sysIcmp6StatErrCksum OBJECT-TYPE 
	SYNTAX Counter64
	MAX-ACCESS read-only
	STATUS current
	DESCRIPTION
		"The number of ICMP messages which the entity received but 
		determined as having ICMP-specific errors, bad ICMP checksums."
	::= { sysGlobalIcmp6Stat 6 } 

sysIcmp6StatErrLen OBJECT-TYPE 
	SYNTAX Counter64
	MAX-ACCESS read-only
	STATUS current
	DESCRIPTION
		"The number of ICMP messages which the entity received but 
			determined as having ICMP-specific errors, bad ICMP bad length."
	::= { sysGlobalIcmp6Stat 7 } 

sysIcmp6StatErrMem OBJECT-TYPE 
	SYNTAX Counter64
	MAX-ACCESS read-only
	STATUS current
	DESCRIPTION
		"The number of memory allocation errors in the process."
	::= { sysGlobalIcmp6Stat 8 } 

sysIcmp6StatErrRtx OBJECT-TYPE 
	SYNTAX Counter64
	MAX-ACCESS read-only
	STATUS current
	DESCRIPTION
		"The number of routing errors."
	::= { sysGlobalIcmp6Stat 9 } 

sysIcmp6StatErrProto OBJECT-TYPE 
	SYNTAX Counter64
	MAX-ACCESS read-only
	STATUS current
	DESCRIPTION
		"The number of ICMP messages which the entity received but
		determined as having protocol errors."
	::= { sysGlobalIcmp6Stat 10 } 

sysIcmp6StatErrOpt OBJECT-TYPE 
	SYNTAX Counter64
	MAX-ACCESS read-only
	STATUS current
	DESCRIPTION
		"The number of errors in options."
	::= { sysGlobalIcmp6Stat 11 } 

sysIcmp6StatErr OBJECT-TYPE 
	SYNTAX Counter64
	MAX-ACCESS read-only
	STATUS current
	DESCRIPTION
		"The number of other not specified errors."
	::= { sysGlobalIcmp6Stat 12 } 

--==================================================================
-- Ip_stat
--==================================================================
sysIpStatResetStats OBJECT-TYPE 
	SYNTAX INTEGER
	MAX-ACCESS read-write
	STATUS current
	DESCRIPTION
		"The action to reset resetable statistics data in  sysGlobalIpStat. 
		 Setting this value to 1 will reset statistics data. 
		 Note, some statistics data may not be reset including data that are incremental counters."
	::= { sysGlobalIpStat 1 } 

sysIpStatTx OBJECT-TYPE 
	SYNTAX Counter64
	MAX-ACCESS read-only
	STATUS current
	DESCRIPTION
		"The total number of transmitted datagrams to interfaces."
	::= { sysGlobalIpStat 2 } 

sysIpStatRx OBJECT-TYPE 
	SYNTAX Counter64
	MAX-ACCESS read-only
	STATUS current
	DESCRIPTION
		"The total number of received datagrams from interfaces."
	::= { sysGlobalIpStat 3 } 

sysIpStatDropped OBJECT-TYPE 
	SYNTAX Counter64
	MAX-ACCESS read-only
	STATUS current
	DESCRIPTION
		"The total number of dropped datagrams."
	::= { sysGlobalIpStat 4 } 

sysIpStatRxFrag OBJECT-TYPE 
	SYNTAX Counter64
	MAX-ACCESS read-only
	STATUS current
	DESCRIPTION
		"The number of received IP datagrams that have been successfully 
		fragmented at this entity."
	::= { sysGlobalIpStat 5 } 

sysIpStatRxFragDropped OBJECT-TYPE 
	SYNTAX Counter64
	MAX-ACCESS read-only
	STATUS current
	DESCRIPTION
		"The number of received IP datagrams that have been dropped
		because they needed to be fragmented at this entity but could 
		not be."
	::= { sysGlobalIpStat 6 } 

sysIpStatTxFrag OBJECT-TYPE 
	SYNTAX Counter64
	MAX-ACCESS read-only
	STATUS current
	DESCRIPTION
		"The number of transmitted IP datagrams that have been successfully 
		fragmented at this entity."
	::= { sysGlobalIpStat 7 } 

sysIpStatTxFragDropped OBJECT-TYPE 
	SYNTAX Counter64
	MAX-ACCESS read-only
	STATUS current
	DESCRIPTION
		"The number of transmitted IP datagrams that have been dropped
		because they needed to be fragmented at this entity but could 
		not be."
	::= { sysGlobalIpStat 8 } 

sysIpStatReassembled OBJECT-TYPE 
	SYNTAX Counter64
	MAX-ACCESS read-only
	STATUS current
	DESCRIPTION
		"The number of IP datagrams successfully reassembled."
	::= { sysGlobalIpStat 9 } 

sysIpStatErrCksum OBJECT-TYPE 
	SYNTAX Counter64
	MAX-ACCESS read-only
	STATUS current
	DESCRIPTION
		"The number of datagrams discarded due to errors in their
		IP headers, bad checksums."
	::= { sysGlobalIpStat 10 } 

sysIpStatErrLen OBJECT-TYPE 
	SYNTAX Counter64
	MAX-ACCESS read-only
	STATUS current
	DESCRIPTION
		"The number of IP datagrams discarded due to errors in their
		IP headers, bad length."
	::= { sysGlobalIpStat 11 } 

sysIpStatErrMem OBJECT-TYPE 
	SYNTAX Counter64
	MAX-ACCESS read-only
	STATUS current
	DESCRIPTION
		"The number of memory allocation errors in the packet process."
	::= { sysGlobalIpStat 12 } 

sysIpStatErrRtx OBJECT-TYPE 
	SYNTAX Counter64
	MAX-ACCESS read-only
	STATUS current
	DESCRIPTION
		"The number of routing errors."
	::= { sysGlobalIpStat 13 } 

sysIpStatErrProto OBJECT-TYPE 
	SYNTAX Counter64
	MAX-ACCESS read-only
	STATUS current
	DESCRIPTION
		"The number of IP datagrams discarded due to errors in their
		protocols."
	::= { sysGlobalIpStat 14 } 

sysIpStatErrOpt OBJECT-TYPE 
	SYNTAX Counter64
	MAX-ACCESS read-only
	STATUS current
	DESCRIPTION
		"The number of errors in options."
	::= { sysGlobalIpStat 15 } 

sysIpStatErrReassembledTooLong OBJECT-TYPE 
	SYNTAX Counter64
	MAX-ACCESS read-only
	STATUS current
	DESCRIPTION
		"The number of IP datagrams discarded due to errors of 
		reassembled too long."
	::= { sysGlobalIpStat 16 } 

--==================================================================
-- Ip6_stat
--==================================================================
sysIp6StatResetStats OBJECT-TYPE 
	SYNTAX INTEGER
	MAX-ACCESS read-write
	STATUS current
	DESCRIPTION
		"The action to reset resetable statistics data in  sysGlobalIp6Stat. 
		 Setting this value to 1 will reset statistics data. 
		 Note, some statistics data may not be reset including data that are incremental counters."
	::= { sysGlobalIp6Stat 1 } 

sysIp6StatTx OBJECT-TYPE 
	SYNTAX Counter64
	MAX-ACCESS read-only
	STATUS current
	DESCRIPTION
		"The total number of transmitted datagrams to interfaces."
	::= { sysGlobalIp6Stat 2 } 

sysIp6StatRx OBJECT-TYPE 
	SYNTAX Counter64
	MAX-ACCESS read-only
	STATUS current
	DESCRIPTION
		"The total number of received datagrams from interfaces."
	::= { sysGlobalIp6Stat 3 } 

sysIp6StatDropped OBJECT-TYPE 
	SYNTAX Counter64
	MAX-ACCESS read-only
	STATUS current
	DESCRIPTION
		"The total number of dropped datagrams."
	::= { sysGlobalIp6Stat 4 } 

sysIp6StatRxFrag OBJECT-TYPE 
	SYNTAX Counter64
	MAX-ACCESS read-only
	STATUS current
	DESCRIPTION
		"The number of received IP datagrams that have been successfully 
		fragmented at this entity."
	::= { sysGlobalIp6Stat 5 } 

sysIp6StatRxFragDropped OBJECT-TYPE 
	SYNTAX Counter64
	MAX-ACCESS read-only
	STATUS current
	DESCRIPTION
		"The number of received IP datagrams that have been dropped
		because they needed to be fragmented at this entity but could 
		not be."
	::= { sysGlobalIp6Stat 6 } 

sysIp6StatTxFrag OBJECT-TYPE 
	SYNTAX Counter64
	MAX-ACCESS read-only
	STATUS current
	DESCRIPTION
		"The number of transmitted IP datagrams that have been successfully 
		fragmented at this entity."
	::= { sysGlobalIp6Stat 7 } 

sysIp6StatTxFragDropped OBJECT-TYPE 
	SYNTAX Counter64
	MAX-ACCESS read-only
	STATUS current
	DESCRIPTION
		"The number of transmitted IP datagrams that have been dropped
		because they needed to be fragmented at this entity but could 
		not be."
	::= { sysGlobalIp6Stat 8 } 

sysIp6StatReassembled OBJECT-TYPE 
	SYNTAX Counter64
	MAX-ACCESS read-only
	STATUS current
	DESCRIPTION
		"The number of IP datagrams successfully reassembled."
	::= { sysGlobalIp6Stat 9 } 

sysIp6StatErrCksum OBJECT-TYPE 
	SYNTAX Counter64
	MAX-ACCESS read-only
	STATUS current
	DESCRIPTION
		"The number of datagrams discarded due to errors in their
		IP headers, bad checksums."
	::= { sysGlobalIp6Stat 10 } 

sysIp6StatErrLen OBJECT-TYPE 
	SYNTAX Counter64
	MAX-ACCESS read-only
	STATUS current
	DESCRIPTION
		"The number of IP datagrams discarded due to errors in their
		IP headers, bad length."
	::= { sysGlobalIp6Stat 11 } 

sysIp6StatErrMem OBJECT-TYPE 
	SYNTAX Counter64
	MAX-ACCESS read-only
	STATUS current
	DESCRIPTION
		"The number of memory allocation errors in the packet process."
	::= { sysGlobalIp6Stat 12 } 

sysIp6StatErrRtx OBJECT-TYPE 
	SYNTAX Counter64
	MAX-ACCESS read-only
	STATUS current
	DESCRIPTION
		"The number of routing errors."
	::= { sysGlobalIp6Stat 13 } 

sysIp6StatErrProto OBJECT-TYPE 
	SYNTAX Counter64
	MAX-ACCESS read-only
	STATUS current
	DESCRIPTION
		"The number of IP datagrams discarded due to errors in their
		protocols."
	::= { sysGlobalIp6Stat 14 } 

sysIp6StatErrOpt OBJECT-TYPE 
	SYNTAX Counter64
	MAX-ACCESS read-only
	STATUS current
	DESCRIPTION
		"The number of errors in options."
	::= { sysGlobalIp6Stat 15 } 

sysIp6StatErrReassembledTooLong OBJECT-TYPE 
	SYNTAX Counter64
	MAX-ACCESS read-only
	STATUS current
	DESCRIPTION
		"The number of IP datagrams discarded due to errors of 
		reassembled too long."
	::= { sysGlobalIp6Stat 16 } 

--==================================================================
-- Global_clientssl_stat
--==================================================================
sysClientsslStatResetStats OBJECT-TYPE 
	SYNTAX INTEGER
	MAX-ACCESS read-write
	STATUS current
	DESCRIPTION
		"The action to reset resetable statistics data in  sysGlobalClientSslStat. 
		 Setting this value to 1 will reset statistics data. 
		 Note, some statistics data may not be reset including data that are incremental counters."
	::= { sysGlobalClientSslStat 1 } 

sysClientsslStatCurConns OBJECT-TYPE 
	SYNTAX CounterBasedGauge64
	MAX-ACCESS read-only
	STATUS current
	DESCRIPTION
		"The current number of concurrent connections with 
		 established SSL sessions being maintained by the filter."
	::= { sysGlobalClientSslStat 2 } 

sysClientsslStatMaxConns OBJECT-TYPE 
	SYNTAX Counter64
	MAX-ACCESS read-only
	STATUS current
	DESCRIPTION
		"The maximum number of concurrent connections with 
		 established SSL sessions being maintained by the filter."
	::= { sysGlobalClientSslStat 3 } 

sysClientsslStatCurNativeConns OBJECT-TYPE 
	SYNTAX CounterBasedGauge64
	MAX-ACCESS read-only
	STATUS current
	DESCRIPTION
		"The current number of concurrent native connections with 
		 established SSL sessions being maintained by the filter."
	::= { sysGlobalClientSslStat 4 } 

sysClientsslStatMaxNativeConns OBJECT-TYPE 
	SYNTAX Counter64
	MAX-ACCESS read-only
	STATUS current
	DESCRIPTION
		"The maximum number of concurrent native connections with 
		 established SSL sessions being maintained by the filter."
	::= { sysGlobalClientSslStat 5 } 

sysClientsslStatTotNativeConns OBJECT-TYPE 
	SYNTAX Counter64
	MAX-ACCESS read-only
	STATUS current
	DESCRIPTION
		"The total number of concurrent native connections with 
		 established SSL sessions being maintained by the filter."
	::= { sysGlobalClientSslStat 6 } 

sysClientsslStatCurCompatConns OBJECT-TYPE 
	SYNTAX CounterBasedGauge64
	MAX-ACCESS read-only
	STATUS current
	DESCRIPTION
		"The current number of concurrent compat connections with 
		 established SSL sessions being maintained by the filter."
	::= { sysGlobalClientSslStat 7 } 

sysClientsslStatMaxCompatConns OBJECT-TYPE 
	SYNTAX Counter64
	MAX-ACCESS read-only
	STATUS current
	DESCRIPTION
		"The maximum number of concurrent compat connections with 
		 established SSL sessions being maintained by the filter."
	::= { sysGlobalClientSslStat 8 } 

sysClientsslStatTotCompatConns OBJECT-TYPE 
	SYNTAX Counter64
	MAX-ACCESS read-only
	STATUS current
	DESCRIPTION
		"The total number of concurrent compat connections with 
		 established SSL sessions being maintained by the filter."
	::= { sysGlobalClientSslStat 9 } 

sysClientsslStatEncryptedBytesIn OBJECT-TYPE 
	SYNTAX Counter64
	MAX-ACCESS read-only
	STATUS current
	DESCRIPTION
		"The total encrypted bytes received."
	::= { sysGlobalClientSslStat 10 } 

sysClientsslStatEncryptedBytesOut OBJECT-TYPE 
	SYNTAX Counter64
	MAX-ACCESS read-only
	STATUS current
	DESCRIPTION
		"The total encrypted bytes sent."
	::= { sysGlobalClientSslStat 11 } 

sysClientsslStatDecryptedBytesIn OBJECT-TYPE 
	SYNTAX Counter64
	MAX-ACCESS read-only
	STATUS current
	DESCRIPTION
		"The total decrypted bytes received."
	::= { sysGlobalClientSslStat 12 } 

sysClientsslStatDecryptedBytesOut OBJECT-TYPE 
	SYNTAX Counter64
	MAX-ACCESS read-only
	STATUS current
	DESCRIPTION
		"The total decrypted bytes sent."
	::= { sysGlobalClientSslStat 13 } 

sysClientsslStatRecordsIn OBJECT-TYPE 
	SYNTAX Counter64
	MAX-ACCESS read-only
	STATUS current
	DESCRIPTION
		"The total records received."
	::= { sysGlobalClientSslStat 14 } 

sysClientsslStatRecordsOut OBJECT-TYPE 
	SYNTAX Counter64
	MAX-ACCESS read-only
	STATUS current
	DESCRIPTION
		"The total records sent."
	::= { sysGlobalClientSslStat 15 } 

sysClientsslStatFullyHwAcceleratedConns OBJECT-TYPE 
	SYNTAX Counter64
	MAX-ACCESS read-only
	STATUS current
	DESCRIPTION
		"Fully hardware-accelerated implies usage of the Cavium 
		 Nitrox or similar hardware accelerator such that all 
		 significant cryptographic operations are offloaded, 
		 including but not limited to the SSL handshake (at least 
		 the RSA/DSA/DH operations) and record processing (at least 
		 the bulk cipher plus MAC)."
	::= { sysGlobalClientSslStat 16 } 

sysClientsslStatPartiallyHwAcceleratedConns OBJECT-TYPE 
	SYNTAX Counter64
	MAX-ACCESS read-only
	STATUS current
	DESCRIPTION
		"Partially hardware-accelerated indicates that at least the 
		 RSA decryptions are offloaded."
	::= { sysGlobalClientSslStat 17 } 

sysClientsslStatNonHwAcceleratedConns OBJECT-TYPE 
	SYNTAX Counter64
	MAX-ACCESS read-only
	STATUS current
	DESCRIPTION
		"Non-accelerated connections are those for which no 
		 steady-state hardware acceleration is available (either 
		 because no hardware accelerators are available or because 
		 the necessary cryptographic operations are unsupported).  
		 Because the extent of hardware acceleration may not be known 
		 until a connection has closed (mid-stream SSL handshakes 
		 might renegotiate an SSL session not supported by hardware 
		 acceleration), this statistic will not be updated for a  
		 given connection until it has closed."
	::= { sysGlobalClientSslStat 18 } 

sysClientsslStatPrematureDisconnects OBJECT-TYPE 
	SYNTAX Counter64
	MAX-ACCESS read-only
	STATUS current
	DESCRIPTION
		"The number of connections disconnected before SSL session 
		 establishment: the total number of connections that were 
		 prematurely closed before an SSL session was established, 
		 not including connections in pass-through mode."
	::= { sysGlobalClientSslStat 19 } 

sysClientsslStatMidstreamRenegotiations OBJECT-TYPE 
	SYNTAX Counter64
	MAX-ACCESS read-only
	STATUS current
	DESCRIPTION
		"The number of mid-stream SSL re-negotiations, not including 
		 initial SSL session establishment."
	::= { sysGlobalClientSslStat 20 } 

sysClientsslStatSessCacheCurEntries OBJECT-TYPE 
	SYNTAX CounterBasedGauge64
	MAX-ACCESS read-only
	STATUS current
	DESCRIPTION
		"The number of the current entries in this cache."
	::= { sysGlobalClientSslStat 21 } 

sysClientsslStatSessCacheHits OBJECT-TYPE 
	SYNTAX Counter64
	MAX-ACCESS read-only
	STATUS current
	DESCRIPTION
		"The total number of the cache hits."
	::= { sysGlobalClientSslStat 22 } 

sysClientsslStatSessCacheLookups OBJECT-TYPE 
	SYNTAX Counter64
	MAX-ACCESS read-only
	STATUS current
	DESCRIPTION
		"The total number of the cache lookups."
	::= { sysGlobalClientSslStat 23 } 

sysClientsslStatSessCacheOverflows OBJECT-TYPE 
	SYNTAX Counter64
	MAX-ACCESS read-only
	STATUS current
	DESCRIPTION
		"The total number of the cache overflows."
	::= { sysGlobalClientSslStat 24 } 

sysClientsslStatSessCacheInvalidations OBJECT-TYPE 
	SYNTAX Counter64
	MAX-ACCESS read-only
	STATUS current
	DESCRIPTION
		"The total number of the session invalidations."
	::= { sysGlobalClientSslStat 25 } 

sysClientsslStatPeercertValid OBJECT-TYPE 
	SYNTAX Counter64
	MAX-ACCESS read-only
	STATUS current
	DESCRIPTION
		"The total number of the valid certificates."
	::= { sysGlobalClientSslStat 26 } 

sysClientsslStatPeercertInvalid OBJECT-TYPE 
	SYNTAX Counter64
	MAX-ACCESS read-only
	STATUS current
	DESCRIPTION
		"The total number of the invalid certificates."
	::= { sysGlobalClientSslStat 27 } 

sysClientsslStatPeercertNone OBJECT-TYPE 
	SYNTAX Counter64
	MAX-ACCESS read-only
	STATUS current
	DESCRIPTION
		"The total number of connections without certificates."
	::= { sysGlobalClientSslStat 28 } 

sysClientsslStatHandshakeFailures OBJECT-TYPE 
	SYNTAX Counter64
	MAX-ACCESS read-only
	STATUS current
	DESCRIPTION
		"The total number of  handshake failures."
	::= { sysGlobalClientSslStat 29 } 

sysClientsslStatBadRecords OBJECT-TYPE 
	SYNTAX Counter64
	MAX-ACCESS read-only
	STATUS current
	DESCRIPTION
		"The total number of the bad records."
	::= { sysGlobalClientSslStat 30 } 

sysClientsslStatFatalAlerts OBJECT-TYPE 
	SYNTAX Counter64
	MAX-ACCESS read-only
	STATUS current
	DESCRIPTION
		"The total number of the fatal alerts."
	::= { sysGlobalClientSslStat 31 } 

sysClientsslStatSslv2 OBJECT-TYPE 
	SYNTAX Counter64
	MAX-ACCESS read-only
	STATUS current
	DESCRIPTION
		"The SSL protocol version 2."
	::= { sysGlobalClientSslStat 32 } 

sysClientsslStatSslv3 OBJECT-TYPE 
	SYNTAX Counter64
	MAX-ACCESS read-only
	STATUS current
	DESCRIPTION
		"The SSL protocol version 3."
	::= { sysGlobalClientSslStat 33 } 

sysClientsslStatTlsv1 OBJECT-TYPE 
	SYNTAX Counter64
	MAX-ACCESS read-only
	STATUS current
	DESCRIPTION
		"The SSL TLS protocol version 1."
	::= { sysGlobalClientSslStat 34 } 

sysClientsslStatAdhKeyxchg OBJECT-TYPE 
	SYNTAX Counter64
	MAX-ACCESS read-only
	STATUS current
	DESCRIPTION
		"The anonymous Diffie-Hellman."
	::= { sysGlobalClientSslStat 35 } 

sysClientsslStatDhDssKeyxchg OBJECT-TYPE 
	SYNTAX Counter64
	MAX-ACCESS read-only
	STATUS	 deprecated
	DESCRIPTION
		"Deprecated! DSS certificate is obsolete in BIGIP.
		The diffie-Hellman w/ DSS certificate."
	::= { sysGlobalClientSslStat 36 } 

sysClientsslStatDhRsaKeyxchg OBJECT-TYPE 
	SYNTAX Counter64
	MAX-ACCESS read-only
	STATUS current
	DESCRIPTION
		"The diffie-Hellman w/ RSA certificate."
	::= { sysGlobalClientSslStat 37 } 

sysClientsslStatDssKeyxchg OBJECT-TYPE 
	SYNTAX Counter64
	MAX-ACCESS read-only
	STATUS	 deprecated
	DESCRIPTION
		"Deprecated! DSS certificate is obsolete in BIGIP.
		The DSS certificate."
	::= { sysGlobalClientSslStat 38 } 

sysClientsslStatEdhDssKeyxchg OBJECT-TYPE 
	SYNTAX Counter64
	MAX-ACCESS read-only
	STATUS	 deprecated
	DESCRIPTION
		"Deprecated! DSS certificate is obsolete in BIGIP.
		The ephemeral Diffie-Hellman w/ DSS cert."
	::= { sysGlobalClientSslStat 39 } 

sysClientsslStatRsaKeyxchg OBJECT-TYPE 
	SYNTAX Counter64
	MAX-ACCESS read-only
	STATUS current
	DESCRIPTION
		"The RSA certificate."
	::= { sysGlobalClientSslStat 40 } 

sysClientsslStatNullBulk OBJECT-TYPE 
	SYNTAX Counter64
	MAX-ACCESS read-only
	STATUS current
	DESCRIPTION
		"No encryption."
	::= { sysGlobalClientSslStat 41 } 

sysClientsslStatAesBulk OBJECT-TYPE 
	SYNTAX Counter64
	MAX-ACCESS read-only
	STATUS current
	DESCRIPTION
		"Advances Encryption Standard (CBC)."
	::= { sysGlobalClientSslStat 42 } 

sysClientsslStatDesBulk OBJECT-TYPE 
	SYNTAX Counter64
	MAX-ACCESS read-only
	STATUS current
	DESCRIPTION
		"Digital Encryption Standard (CBC)."
	::= { sysGlobalClientSslStat 43 } 

sysClientsslStatIdeaBulk OBJECT-TYPE 
	SYNTAX Counter64
	MAX-ACCESS read-only
	STATUS current
	DESCRIPTION
		"IDEA (old SSLv2 cipher)."
	::= { sysGlobalClientSslStat 44 } 

sysClientsslStatRc2Bulk OBJECT-TYPE 
	SYNTAX Counter64
	MAX-ACCESS read-only
	STATUS current
	DESCRIPTION
		"Rivest Cipher 2 (CBC)."
	::= { sysGlobalClientSslStat 45 } 

sysClientsslStatRc4Bulk OBJECT-TYPE 
	SYNTAX Counter64
	MAX-ACCESS read-only
	STATUS current
	DESCRIPTION
		"Rivest Cipher 4 (CBC)."
	::= { sysGlobalClientSslStat 46 } 

sysClientsslStatNullDigest OBJECT-TYPE 
	SYNTAX Counter64
	MAX-ACCESS read-only
	STATUS current
	DESCRIPTION
		"No message authentication."
	::= { sysGlobalClientSslStat 47 } 

sysClientsslStatMd5Digest OBJECT-TYPE 
	SYNTAX Counter64
	MAX-ACCESS read-only
	STATUS current
	DESCRIPTION
		"Message Digest 5."
	::= { sysGlobalClientSslStat 48 } 

sysClientsslStatShaDigest OBJECT-TYPE 
	SYNTAX Counter64
	MAX-ACCESS read-only
	STATUS current
	DESCRIPTION
		"Secure Hash Algorithm."
	::= { sysGlobalClientSslStat 49 } 

sysClientsslStatNotssl OBJECT-TYPE 
	SYNTAX Counter64
	MAX-ACCESS read-only
	STATUS current
	DESCRIPTION
		"The total number of the bad client greetings."
	::= { sysGlobalClientSslStat 50 } 

sysClientsslStatEdhRsaKeyxchg OBJECT-TYPE 
	SYNTAX Counter64
	MAX-ACCESS read-only
	STATUS current
	DESCRIPTION
		"Ephemeral Diffie-Hellman w/ RSA cert."
	::= { sysGlobalClientSslStat 51 } 

sysClientsslStatTotConns5s OBJECT-TYPE 
	SYNTAX CounterBasedGauge64
	MAX-ACCESS read-only
	STATUS current
	DESCRIPTION
		"The average total SSL connections from client-side to the system in last five seconds."
	::= { sysGlobalClientSslStat 52 } 

sysClientsslStatTotConns1m OBJECT-TYPE 
	SYNTAX CounterBasedGauge64
	MAX-ACCESS read-only
	STATUS current
	DESCRIPTION
		"The average total SSL connections from client-side to the system in last one minute."
	::= { sysGlobalClientSslStat 53 } 

sysClientsslStatTotConns5m OBJECT-TYPE 
	SYNTAX CounterBasedGauge64
	MAX-ACCESS read-only
	STATUS current
	DESCRIPTION
		"The average total SSL connections from client-side to the system in last five minutes."
	::= { sysGlobalClientSslStat 54 } 

sysClientsslStatSecureHandshakes OBJECT-TYPE 
	SYNTAX Counter64
	MAX-ACCESS read-only
	STATUS current
	DESCRIPTION
		"The number of handshakes, including mid-stream re-negotiations,
			 performed with peers supporting SSL secure renegotiation."
	::= { sysGlobalClientSslStat 55 } 

sysClientsslStatInsecureHandshakeAccepts OBJECT-TYPE 
	SYNTAX Counter64
	MAX-ACCESS read-only
	STATUS current
	DESCRIPTION
		"The number of handshakes, including mid-stream re-negotiations,
			 performed with peers not supporting SSL secure renegotiation."
	::= { sysGlobalClientSslStat 56 } 

sysClientsslStatInsecureHandshakeRejects OBJECT-TYPE 
	SYNTAX Counter64
	MAX-ACCESS read-only
	STATUS current
	DESCRIPTION
		"The number of rejected initial handshakes with peers
			 not supporting SSL secure renegotiation."
	::= { sysGlobalClientSslStat 57 } 

sysClientsslStatInsecureRenegotiationRejects OBJECT-TYPE 
	SYNTAX Counter64
	MAX-ACCESS read-only
	STATUS current
	DESCRIPTION
		"The number of rejected renegotiation attempts by peers
			 not supporting SSL secure renegotiation."
	::= { sysGlobalClientSslStat 58 } 

sysClientsslStatSniRejects OBJECT-TYPE 
	SYNTAX Counter64
	MAX-ACCESS read-only
	STATUS current
	DESCRIPTION
		"The number of rejected handshake attempts by peers
			 not supporting SSL SNI extension or having mismatched
			 server names."
	::= { sysGlobalClientSslStat 59 } 

sysClientsslStatTlsv11 OBJECT-TYPE 
	SYNTAX Counter64
	MAX-ACCESS read-only
	STATUS current
	DESCRIPTION
		"The SSL TLS protocol version 1.1."
	::= { sysGlobalClientSslStat 60 } 

sysClientsslStatTlsv12 OBJECT-TYPE 
	SYNTAX Counter64
	MAX-ACCESS read-only
	STATUS current
	DESCRIPTION
		"The SSL TLS protocol version 1.2."
	::= { sysGlobalClientSslStat 61 } 

sysClientsslStatDtlsv1 OBJECT-TYPE 
	SYNTAX Counter64
	MAX-ACCESS read-only
	STATUS current
	DESCRIPTION
		"The SSL DTLS protocol version 1.0."
	::= { sysGlobalClientSslStat 62 } 

sysClientsslStatEcdheRsaKeyxchg OBJECT-TYPE 
	SYNTAX Counter64
	MAX-ACCESS read-only
	STATUS current
	DESCRIPTION
		"Ephemeral ECDH w/ RSA cert."
	::= { sysGlobalClientSslStat 63 } 

sysClientsslStatConns OBJECT-TYPE 
	SYNTAX Counter64
	MAX-ACCESS read-only
	STATUS current
	DESCRIPTION
		"The total connections using SSL FWDP feature."
	::= { sysGlobalClientSslStat 64 } 

sysClientsslStatCachedCerts OBJECT-TYPE 
	SYNTAX Counter64
	MAX-ACCESS read-only
	STATUS current
	DESCRIPTION
		"The total SSL FWDP cached certificates."
	::= { sysGlobalClientSslStat 65 } 

--==================================================================
-- Global_serverssl_stat
--==================================================================
sysServersslStatResetStats OBJECT-TYPE 
	SYNTAX INTEGER
	MAX-ACCESS read-write
	STATUS current
	DESCRIPTION
		"The action to reset resetable statistics data in  sysGlobalServerSslStat. 
		 Setting this value to 1 will reset statistics data. 
		 Note, some statistics data may not be reset including data that are incremental counters."
	::= { sysGlobalServerSslStat 1 } 

sysServersslStatCurConns OBJECT-TYPE 
	SYNTAX CounterBasedGauge64
	MAX-ACCESS read-only
	STATUS current
	DESCRIPTION
		"The current number of concurrent connections with 
		 established SSL sessions being maintained by the filter."
	::= { sysGlobalServerSslStat 2 } 

sysServersslStatMaxConns OBJECT-TYPE 
	SYNTAX Counter64
	MAX-ACCESS read-only
	STATUS current
	DESCRIPTION
		"The maximum number of concurrent connections with 
		 established SSL sessions being maintained by the filter."
	::= { sysGlobalServerSslStat 3 } 

sysServersslStatCurNativeConns OBJECT-TYPE 
	SYNTAX CounterBasedGauge64
	MAX-ACCESS read-only
	STATUS current
	DESCRIPTION
		"The current number of concurrent native connections with 
		 established SSL sessions being maintained by the filter."
	::= { sysGlobalServerSslStat 4 } 

sysServersslStatMaxNativeConns OBJECT-TYPE 
	SYNTAX Counter64
	MAX-ACCESS read-only
	STATUS current
	DESCRIPTION
		"The maximum number of concurrent native connections with 
		 established SSL sessions being maintained by the filter."
	::= { sysGlobalServerSslStat 5 } 

sysServersslStatTotNativeConns OBJECT-TYPE 
	SYNTAX Counter64
	MAX-ACCESS read-only
	STATUS current
	DESCRIPTION
		"The total number of concurrent native connections with 
		 established SSL sessions being maintained by the filter."
	::= { sysGlobalServerSslStat 6 } 

sysServersslStatCurCompatConns OBJECT-TYPE 
	SYNTAX CounterBasedGauge64
	MAX-ACCESS read-only
	STATUS current
	DESCRIPTION
		"The current number of concurrent compat connections with 
		 established SSL sessions being maintained by the filter."
	::= { sysGlobalServerSslStat 7 } 

sysServersslStatMaxCompatConns OBJECT-TYPE 
	SYNTAX Counter64
	MAX-ACCESS read-only
	STATUS current
	DESCRIPTION
		"The maximum number of concurrent compat connections with 
		 established SSL sessions being maintained by the filter."
	::= { sysGlobalServerSslStat 8 } 

sysServersslStatTotCompatConns OBJECT-TYPE 
	SYNTAX Counter64
	MAX-ACCESS read-only
	STATUS current
	DESCRIPTION
		"The total number of concurrent compat connections with 
		 established SSL sessions being maintained by the filter."
	::= { sysGlobalServerSslStat 9 } 

sysServersslStatEncryptedBytesIn OBJECT-TYPE 
	SYNTAX Counter64
	MAX-ACCESS read-only
	STATUS current
	DESCRIPTION
		"The total encrypted bytes received."
	::= { sysGlobalServerSslStat 10 } 

sysServersslStatEncryptedBytesOut OBJECT-TYPE 
	SYNTAX Counter64
	MAX-ACCESS read-only
	STATUS current
	DESCRIPTION
		"The total encrypted bytes sent."
	::= { sysGlobalServerSslStat 11 } 

sysServersslStatDecryptedBytesIn OBJECT-TYPE 
	SYNTAX Counter64
	MAX-ACCESS read-only
	STATUS current
	DESCRIPTION
		"The total decrypted bytes received."
	::= { sysGlobalServerSslStat 12 } 

sysServersslStatDecryptedBytesOut OBJECT-TYPE 
	SYNTAX Counter64
	MAX-ACCESS read-only
	STATUS current
	DESCRIPTION
		"The total decrypted bytes sent."
	::= { sysGlobalServerSslStat 13 } 

sysServersslStatRecordsIn OBJECT-TYPE 
	SYNTAX Counter64
	MAX-ACCESS read-only
	STATUS current
	DESCRIPTION
		"The total records received."
	::= { sysGlobalServerSslStat 14 } 

sysServersslStatRecordsOut OBJECT-TYPE 
	SYNTAX Counter64
	MAX-ACCESS read-only
	STATUS current
	DESCRIPTION
		"The total records sent."
	::= { sysGlobalServerSslStat 15 } 

sysServersslStatFullyHwAcceleratedConns OBJECT-TYPE 
	SYNTAX Counter64
	MAX-ACCESS read-only
	STATUS current
	DESCRIPTION
		"Fully hardware-accelerated implies usage of the Cavium 
		 Nitrox or similar hardware accelerator such that all 
		 significant cryptographic operations are offloaded, 
		 including but not limited to the SSL handshake (at least 
		 the RSA/DSA/DH operations) and record processing (at least 
		 the bulk cipher plus MAC)."
	::= { sysGlobalServerSslStat 16 } 

sysServersslStatPartiallyHwAcceleratedConns OBJECT-TYPE 
	SYNTAX Counter64
	MAX-ACCESS read-only
	STATUS current
	DESCRIPTION
		"Partially hardware-accelerated indicates that at least the 
		 RSA decryptions are offloaded."
	::= { sysGlobalServerSslStat 17 } 

sysServersslStatNonHwAcceleratedConns OBJECT-TYPE 
	SYNTAX Counter64
	MAX-ACCESS read-only
	STATUS current
	DESCRIPTION
		"Non-accelerated connections are those for which no 
		 steady-state hardware acceleration is available (either 
		 because no hardware accelerators are available or because 
		 the necessary cryptographic operations are unsupported).  
		 Because the extent of hardware acceleration may not be known 
		 until a connection has closed (mid-stream SSL handshakes 
		 might renegotiate an SSL session not supported by hardware 
		 acceleration), this statistic will not be updated for a  
		 given connection until it has closed."
	::= { sysGlobalServerSslStat 18 } 

sysServersslStatPrematureDisconnects OBJECT-TYPE 
	SYNTAX Counter64
	MAX-ACCESS read-only
	STATUS current
	DESCRIPTION
		"The number of connections disconnected before SSL session 
		 establishment: the total number of connections that were 
		 prematurely closed before an SSL session was established, 
		 not including connections in pass-through mode."
	::= { sysGlobalServerSslStat 19 } 

sysServersslStatMidstreamRenegotiations OBJECT-TYPE 
	SYNTAX Counter64
	MAX-ACCESS read-only
	STATUS current
	DESCRIPTION
		"The number of mid-stream SSL re-negotiations, not including 
		 initial SSL session establishment."
	::= { sysGlobalServerSslStat 20 } 

sysServersslStatSessCacheCurEntries OBJECT-TYPE 
	SYNTAX CounterBasedGauge64
	MAX-ACCESS read-only
	STATUS current
	DESCRIPTION
		"The number of the current entries in this cache."
	::= { sysGlobalServerSslStat 21 } 

sysServersslStatSessCacheHits OBJECT-TYPE 
	SYNTAX Counter64
	MAX-ACCESS read-only
	STATUS current
	DESCRIPTION
		"The total number of the cache hits."
	::= { sysGlobalServerSslStat 22 } 

sysServersslStatSessCacheLookups OBJECT-TYPE 
	SYNTAX Counter64
	MAX-ACCESS read-only
	STATUS current
	DESCRIPTION
		"The total number of the cache lookups."
	::= { sysGlobalServerSslStat 23 } 

sysServersslStatSessCacheOverflows OBJECT-TYPE 
	SYNTAX Counter64
	MAX-ACCESS read-only
	STATUS current
	DESCRIPTION
		"The total number of the cache overflows."
	::= { sysGlobalServerSslStat 24 } 

sysServersslStatSessCacheInvalidations OBJECT-TYPE 
	SYNTAX Counter64
	MAX-ACCESS read-only
	STATUS current
	DESCRIPTION
		"The total number of the session invalidations."
	::= { sysGlobalServerSslStat 25 } 

sysServersslStatPeercertValid OBJECT-TYPE 
	SYNTAX Counter64
	MAX-ACCESS read-only
	STATUS current
	DESCRIPTION
		"The total number of the valid certificates."
	::= { sysGlobalServerSslStat 26 } 

sysServersslStatPeercertInvalid OBJECT-TYPE 
	SYNTAX Counter64
	MAX-ACCESS read-only
	STATUS current
	DESCRIPTION
		"The total number of the invalid certificates."
	::= { sysGlobalServerSslStat 27 } 

sysServersslStatPeercertNone OBJECT-TYPE 
	SYNTAX Counter64
	MAX-ACCESS read-only
	STATUS current
	DESCRIPTION
		"The total number of connections without certificates."
	::= { sysGlobalServerSslStat 28 } 

sysServersslStatHandshakeFailures OBJECT-TYPE 
	SYNTAX Counter64
	MAX-ACCESS read-only
	STATUS current
	DESCRIPTION
		"The total number of handshake failures."
	::= { sysGlobalServerSslStat 29 } 

sysServersslStatBadRecords OBJECT-TYPE 
	SYNTAX Counter64
	MAX-ACCESS read-only
	STATUS current
	DESCRIPTION
		"The total number of the bad records."
	::= { sysGlobalServerSslStat 30 } 

sysServersslStatFatalAlerts OBJECT-TYPE 
	SYNTAX Counter64
	MAX-ACCESS read-only
	STATUS current
	DESCRIPTION
		"The total number of the fatal alerts."
	::= { sysGlobalServerSslStat 31 } 

sysServersslStatSslv2 OBJECT-TYPE 
	SYNTAX Counter64
	MAX-ACCESS read-only
	STATUS current
	DESCRIPTION
		"The SSL protocol version 2."
	::= { sysGlobalServerSslStat 32 } 

sysServersslStatSslv3 OBJECT-TYPE 
	SYNTAX Counter64
	MAX-ACCESS read-only
	STATUS current
	DESCRIPTION
		"The SSL protocol version 3."
	::= { sysGlobalServerSslStat 33 } 

sysServersslStatTlsv1 OBJECT-TYPE 
	SYNTAX Counter64
	MAX-ACCESS read-only
	STATUS current
	DESCRIPTION
		"The SSL TLS protocol version 1."
	::= { sysGlobalServerSslStat 34 } 

sysServersslStatAdhKeyxchg OBJECT-TYPE 
	SYNTAX Counter64
	MAX-ACCESS read-only
	STATUS current
	DESCRIPTION
		"The anonymous Diffie-Hellman."
	::= { sysGlobalServerSslStat 35 } 

sysServersslStatDhDssKeyxchg OBJECT-TYPE 
	SYNTAX Counter64
	MAX-ACCESS read-only
	STATUS	 deprecated
	DESCRIPTION
		"Deprecated! DSS certificate is obsolete in BIGIP.
		The diffie-Hellman w/ DSS certificate."
	::= { sysGlobalServerSslStat 36 } 

sysServersslStatDhRsaKeyxchg OBJECT-TYPE 
	SYNTAX Counter64
	MAX-ACCESS read-only
	STATUS current
	DESCRIPTION
		"The diffie-Hellman w/ RSA certificate."
	::= { sysGlobalServerSslStat 37 } 

sysServersslStatDssKeyxchg OBJECT-TYPE 
	SYNTAX Counter64
	MAX-ACCESS read-only
	STATUS	 deprecated
	DESCRIPTION
		"Deprecated! DSS certificate is obsolete in BIGIP.
		The DSS certificate."
	::= { sysGlobalServerSslStat 38 } 

sysServersslStatEdhDssKeyxchg OBJECT-TYPE 
	SYNTAX Counter64
	MAX-ACCESS read-only
	STATUS	 deprecated
	DESCRIPTION
		"Deprecated! DSS certificate is obsolete in BIGIP.
		The ephemeral Diffie-Hellman w/ DSS cert."
	::= { sysGlobalServerSslStat 39 } 

sysServersslStatRsaKeyxchg OBJECT-TYPE 
	SYNTAX Counter64
	MAX-ACCESS read-only
	STATUS current
	DESCRIPTION
		"The RSA certificate."
	::= { sysGlobalServerSslStat 40 } 

sysServersslStatNullBulk OBJECT-TYPE 
	SYNTAX Counter64
	MAX-ACCESS read-only
	STATUS current
	DESCRIPTION
		"No encryption."
	::= { sysGlobalServerSslStat 41 } 

sysServersslStatAesBulk OBJECT-TYPE 
	SYNTAX Counter64
	MAX-ACCESS read-only
	STATUS current
	DESCRIPTION
		"Advances Encryption Standard (CBC)."
	::= { sysGlobalServerSslStat 42 } 

sysServersslStatDesBulk OBJECT-TYPE 
	SYNTAX Counter64
	MAX-ACCESS read-only
	STATUS current
	DESCRIPTION
		"Digital Encryption Standard (CBC)."
	::= { sysGlobalServerSslStat 43 } 

sysServersslStatIdeaBulk OBJECT-TYPE 
	SYNTAX Counter64
	MAX-ACCESS read-only
	STATUS current
	DESCRIPTION
		"IDEA (old SSLv2 cipher)."
	::= { sysGlobalServerSslStat 44 } 

sysServersslStatRc2Bulk OBJECT-TYPE 
	SYNTAX Counter64
	MAX-ACCESS read-only
	STATUS current
	DESCRIPTION
		"Rivest Cipher 2 (CBC)."
	::= { sysGlobalServerSslStat 45 } 

sysServersslStatRc4Bulk OBJECT-TYPE 
	SYNTAX Counter64
	MAX-ACCESS read-only
	STATUS current
	DESCRIPTION
		"Rivest Cipher 4 (CBC)."
	::= { sysGlobalServerSslStat 46 } 

sysServersslStatNullDigest OBJECT-TYPE 
	SYNTAX Counter64
	MAX-ACCESS read-only
	STATUS current
	DESCRIPTION
		"No message authentication."
	::= { sysGlobalServerSslStat 47 } 

sysServersslStatMd5Digest OBJECT-TYPE 
	SYNTAX Counter64
	MAX-ACCESS read-only
	STATUS current
	DESCRIPTION
		"Message Digest 5."
	::= { sysGlobalServerSslStat 48 } 

sysServersslStatShaDigest OBJECT-TYPE 
	SYNTAX Counter64
	MAX-ACCESS read-only
	STATUS current
	DESCRIPTION
		"Secure Hash Algorithm."
	::= { sysGlobalServerSslStat 49 } 

sysServersslStatNotssl OBJECT-TYPE 
	SYNTAX Counter64
	MAX-ACCESS read-only
	STATUS current
	DESCRIPTION
		"The total number of the bad client greetings."
	::= { sysGlobalServerSslStat 50 } 

sysServersslStatEdhRsaKeyxchg OBJECT-TYPE 
	SYNTAX Counter64
	MAX-ACCESS read-only
	STATUS current
	DESCRIPTION
		"Ephemeral Diffie-Hellman w/ RSA cert."
	::= { sysGlobalServerSslStat 51 } 

sysServersslStatSecureHandshakes OBJECT-TYPE 
	SYNTAX Counter64
	MAX-ACCESS read-only
	STATUS current
	DESCRIPTION
		"The number of handshakes, including mid-stream re-negotiations,
			 performed with peers supporting SSL secure renegotiation."
	::= { sysGlobalServerSslStat 52 } 

sysServersslStatInsecureHandshakeAccepts OBJECT-TYPE 
	SYNTAX Counter64
	MAX-ACCESS read-only
	STATUS current
	DESCRIPTION
		"The number of handshakes, including mid-stream re-negotiations,
			 performed with peers not supporting SSL secure renegotiation."
	::= { sysGlobalServerSslStat 53 } 

sysServersslStatInsecureHandshakeRejects OBJECT-TYPE 
	SYNTAX Counter64
	MAX-ACCESS read-only
	STATUS current
	DESCRIPTION
		"The number of rejected initial handshakes with peers
			 not supporting SSL secure renegotiation."
	::= { sysGlobalServerSslStat 54 } 

sysServersslStatInsecureRenegotiationRejects OBJECT-TYPE 
	SYNTAX Counter64
	MAX-ACCESS read-only
	STATUS current
	DESCRIPTION
		"The number of rejected renegotiation attempts by peers
			 not supporting SSL secure renegotiation."
	::= { sysGlobalServerSslStat 55 } 

sysServersslStatSniRejects OBJECT-TYPE 
	SYNTAX Counter64
	MAX-ACCESS read-only
	STATUS current
	DESCRIPTION
		"The number of rejected handshake attempts by peers
			 not supporting SSL SNI extension or having mismatched
			 server names."
	::= { sysGlobalServerSslStat 56 } 

sysServersslStatTlsv11 OBJECT-TYPE 
	SYNTAX Counter64
	MAX-ACCESS read-only
	STATUS current
	DESCRIPTION
		"The SSL TLS protocol version 1.1."
	::= { sysGlobalServerSslStat 57 } 

sysServersslStatTlsv12 OBJECT-TYPE 
	SYNTAX Counter64
	MAX-ACCESS read-only
	STATUS current
	DESCRIPTION
		"The SSL TLS protocol version 1.2."
	::= { sysGlobalServerSslStat 58 } 

sysServersslStatDtlsv1 OBJECT-TYPE 
	SYNTAX Counter64
	MAX-ACCESS read-only
	STATUS current
	DESCRIPTION
		"The SSL DTLS protocol version 1.0."
	::= { sysGlobalServerSslStat 59 } 

sysServersslStatEcdheRsaKeyxchg OBJECT-TYPE 
	SYNTAX Counter64
	MAX-ACCESS read-only
	STATUS current
	DESCRIPTION
		"Ephemeral ECDH w/ RSA cert."
	::= { sysGlobalServerSslStat 60 } 

sysServersslStatConns OBJECT-TYPE 
	SYNTAX Counter64
	MAX-ACCESS read-only
	STATUS current
	DESCRIPTION
		"The total connections using SSL FWDP feature."
	::= { sysGlobalServerSslStat 61 } 

--==================================================================
-- Global_stream_stat
--==================================================================
sysStreamStatResetStats OBJECT-TYPE 
	SYNTAX INTEGER
	MAX-ACCESS read-write
	STATUS current
	DESCRIPTION
		"The action to reset resetable statistics data in  sysGlobalStreamStat. 
		 Setting this value to 1 will reset statistics data. 
		 Note, some statistics data may not be reset including data that are incremental counters."
	::= { sysGlobalStreamStat 1 } 

sysStreamStatReplaces OBJECT-TYPE 
	SYNTAX Counter64
	MAX-ACCESS read-only
	STATUS current
	DESCRIPTION
		"The number of replace operations completed on the system."
	::= { sysGlobalStreamStat 2 } 

--==================================================================
-- Global_tcp_stat
--==================================================================
sysTcpStatResetStats OBJECT-TYPE 
	SYNTAX INTEGER
	MAX-ACCESS read-write
	STATUS current
	DESCRIPTION
		"The action to reset resetable statistics data in  sysGlobalTcpStat. 
		 Setting this value to 1 will reset statistics data. 
		 Note, some statistics data may not be reset including data that are incremental counters."
	::= { sysGlobalTcpStat 1 } 

sysTcpStatOpen OBJECT-TYPE 
	SYNTAX Integer32
	MAX-ACCESS read-only
	STATUS current
	DESCRIPTION
		"The number of current open connections."
	::= { sysGlobalTcpStat 2 } 

sysTcpStatCloseWait OBJECT-TYPE 
	SYNTAX Integer32
	MAX-ACCESS read-only
	STATUS current
	DESCRIPTION
		"The number of current connections in CLOSE-WAIT/LAST-ACK."
	::= { sysGlobalTcpStat 3 } 

sysTcpStatFinWait OBJECT-TYPE 
	SYNTAX Integer32
	MAX-ACCESS read-only
	STATUS current
	DESCRIPTION
		"The number of current connections in FIN-WAIT/CLOSING."
	::= { sysGlobalTcpStat 4 } 

sysTcpStatTimeWait OBJECT-TYPE 
	SYNTAX Integer32
	MAX-ACCESS read-only
	STATUS current
	DESCRIPTION
		"The number of current connections in TIME-WAIT."
	::= { sysGlobalTcpStat 5 } 

sysTcpStatAccepts OBJECT-TYPE 
	SYNTAX Counter64
	MAX-ACCESS read-only
	STATUS current
	DESCRIPTION
		"The number of connections accepted."
	::= { sysGlobalTcpStat 6 } 

sysTcpStatAcceptfails OBJECT-TYPE 
	SYNTAX Counter64
	MAX-ACCESS read-only
	STATUS current
	DESCRIPTION
		"The number of connections not accepted."
	::= { sysGlobalTcpStat 7 } 

sysTcpStatConnects OBJECT-TYPE 
	SYNTAX Counter64
	MAX-ACCESS read-only
	STATUS current
	DESCRIPTION
		"The number of connections established."
	::= { sysGlobalTcpStat 8 } 

sysTcpStatConnfails OBJECT-TYPE 
	SYNTAX Counter64
	MAX-ACCESS read-only
	STATUS current
	DESCRIPTION
		"The number of connections failures."
	::= { sysGlobalTcpStat 9 } 

sysTcpStatExpires OBJECT-TYPE 
	SYNTAX Counter64
	MAX-ACCESS read-only
	STATUS current
	DESCRIPTION
		"The number of connections expired due to idle timeout."
	::= { sysGlobalTcpStat 10 } 

sysTcpStatAbandons OBJECT-TYPE 
	SYNTAX Counter64
	MAX-ACCESS read-only
	STATUS current
	DESCRIPTION
		"The number of connections abandoned connections due to 
		retries/keep-alives."
	::= { sysGlobalTcpStat 11 } 

sysTcpStatRxrst OBJECT-TYPE 
	SYNTAX Counter64
	MAX-ACCESS read-only
	STATUS current
	DESCRIPTION
		"The number of received RST."
	::= { sysGlobalTcpStat 12 } 

sysTcpStatRxbadsum OBJECT-TYPE 
	SYNTAX Counter64
	MAX-ACCESS read-only
	STATUS current
	DESCRIPTION
		"The number of bad checksum."
	::= { sysGlobalTcpStat 13 } 

sysTcpStatRxbadseg OBJECT-TYPE 
	SYNTAX Counter64
	MAX-ACCESS read-only
	STATUS current
	DESCRIPTION
		"The number of malformed segments."
	::= { sysGlobalTcpStat 14 } 

sysTcpStatRxooseg OBJECT-TYPE 
	SYNTAX Counter64
	MAX-ACCESS read-only
	STATUS current
	DESCRIPTION
		"The number of out of order segments."
	::= { sysGlobalTcpStat 15 } 

sysTcpStatRxcookie OBJECT-TYPE 
	SYNTAX Counter64
	MAX-ACCESS read-only
	STATUS current
	DESCRIPTION
		"The number of received SYN-cookies."
	::= { sysGlobalTcpStat 16 } 

sysTcpStatRxbadcookie OBJECT-TYPE 
	SYNTAX Counter64
	MAX-ACCESS read-only
	STATUS current
	DESCRIPTION
		"The number of bad SYN-cookies."
	::= { sysGlobalTcpStat 17 } 

sysTcpStatSyncacheover OBJECT-TYPE 
	SYNTAX Counter64
	MAX-ACCESS read-only
	STATUS current
	DESCRIPTION
		"The number of SYN-cache overflow."
	::= { sysGlobalTcpStat 18 } 

sysTcpStatTxrexmits OBJECT-TYPE 
	SYNTAX Counter64
	MAX-ACCESS read-only
	STATUS current
	DESCRIPTION
		"The number of retransmitted segments."
	::= { sysGlobalTcpStat 19 } 

--==================================================================
-- Global_udp_stat
--==================================================================
sysUdpStatResetStats OBJECT-TYPE 
	SYNTAX INTEGER
	MAX-ACCESS read-write
	STATUS current
	DESCRIPTION
		"The action to reset resetable statistics data in  sysGlobalUdpStat. 
		 Setting this value to 1 will reset statistics data. 
		 Note, some statistics data may not be reset including data that are incremental counters."
	::= { sysGlobalUdpStat 1 } 

sysUdpStatOpen OBJECT-TYPE 
	SYNTAX Integer32
	MAX-ACCESS read-only
	STATUS current
	DESCRIPTION
		"The number of current open connections."
	::= { sysGlobalUdpStat 2 } 

sysUdpStatAccepts OBJECT-TYPE 
	SYNTAX Counter64
	MAX-ACCESS read-only
	STATUS current
	DESCRIPTION
		"The number of connections accepted."
	::= { sysGlobalUdpStat 3 } 

sysUdpStatAcceptfails OBJECT-TYPE 
	SYNTAX Counter64
	MAX-ACCESS read-only
	STATUS current
	DESCRIPTION
		"The number of connections not accepted."
	::= { sysGlobalUdpStat 4 } 

sysUdpStatConnects OBJECT-TYPE 
	SYNTAX Counter64
	MAX-ACCESS read-only
	STATUS current
	DESCRIPTION
		"The number of connections established."
	::= { sysGlobalUdpStat 5 } 

sysUdpStatConnfails OBJECT-TYPE 
	SYNTAX Counter64
	MAX-ACCESS read-only
	STATUS current
	DESCRIPTION
		"The number of connections failures."
	::= { sysGlobalUdpStat 6 } 

sysUdpStatExpires OBJECT-TYPE 
	SYNTAX Counter64
	MAX-ACCESS read-only
	STATUS current
	DESCRIPTION
		"The number of connections expired connections due to idle timeout."
	::= { sysGlobalUdpStat 7 } 

sysUdpStatRxdgram OBJECT-TYPE 
	SYNTAX Counter64
	MAX-ACCESS read-only
	STATUS current
	DESCRIPTION
		"The number of received datagrams."
	::= { sysGlobalUdpStat 8 } 

sysUdpStatRxbaddgram OBJECT-TYPE 
	SYNTAX Counter64
	MAX-ACCESS read-only
	STATUS current
	DESCRIPTION
		"The number of malformed datagrams."
	::= { sysGlobalUdpStat 9 } 

sysUdpStatRxunreach OBJECT-TYPE 
	SYNTAX Counter64
	MAX-ACCESS read-only
	STATUS current
	DESCRIPTION
		"The number of received ICMP un-reached."
	::= { sysGlobalUdpStat 10 } 

sysUdpStatRxbadsum OBJECT-TYPE 
	SYNTAX Counter64
	MAX-ACCESS read-only
	STATUS current
	DESCRIPTION
		"The number of bad checksum."
	::= { sysGlobalUdpStat 11 } 

sysUdpStatRxnosum OBJECT-TYPE 
	SYNTAX Counter64
	MAX-ACCESS read-only
	STATUS current
	DESCRIPTION
		"The number of no checksum."
	::= { sysGlobalUdpStat 12 } 

sysUdpStatTxdgram OBJECT-TYPE 
	SYNTAX Counter64
	MAX-ACCESS read-only
	STATUS current
	DESCRIPTION
		"The number of transmitted datagrams."
	::= { sysGlobalUdpStat 13 } 

--==================================================================
-- Admin_ip
--==================================================================
sysAdminIpNumber OBJECT-TYPE 
	SYNTAX INTEGER
	MAX-ACCESS read-only
	STATUS current
	DESCRIPTION
		"The number of sysAdminIp entries in the table."
	::= { sysAdminIp 1 } 

sysAdminIpTable OBJECT-TYPE
	SYNTAX SEQUENCE OF SysAdminIpEntry
	MAX-ACCESS not-accessible
	STATUS current
	DESCRIPTION
		"A table containing information of a device's administrative IP addresses on this machine."
	::= { sysAdminIp 2 } 

sysAdminIpEntry OBJECT-TYPE
	SYNTAX  SysAdminIpEntry
	MAX-ACCESS not-accessible
	STATUS current
	DESCRIPTION
		"Columns in the sysAdminIp Table"
	INDEX {
		sysAdminIpAddrType,
		sysAdminIpAddr
	}
	::= { sysAdminIpTable 1 } 

SysAdminIpEntry ::= 
	SEQUENCE {
        	sysAdminIpAddrType                                     InetAddressType,
        	sysAdminIpAddr                                         InetAddress,
        	sysAdminIpNetmaskType                                  InetAddressType,
        	sysAdminIpNetmask                                      InetAddress,
        	sysAdminIpName                                         LongDisplayString
	}

sysAdminIpAddrType OBJECT-TYPE 
	SYNTAX InetAddressType
	MAX-ACCESS read-only
	STATUS current
	DESCRIPTION
		"The IP address type of sysAdminIpAddr"
	::= { sysAdminIpEntry 1 } 

sysAdminIpAddr OBJECT-TYPE 
	SYNTAX InetAddress
	MAX-ACCESS read-only
	STATUS current
	DESCRIPTION
		"An administrative IP address on this machine. It is 
		 interpreted within the context of a sysAdminIpAddrType value."
	::= { sysAdminIpEntry 2 } 

sysAdminIpNetmaskType OBJECT-TYPE 
	SYNTAX InetAddressType
	MAX-ACCESS read-only
	STATUS current
	DESCRIPTION
		"The netmask type of sysAdminIpNetmask"
	::= { sysAdminIpEntry 3 } 

sysAdminIpNetmask OBJECT-TYPE 
	SYNTAX InetAddress
	MAX-ACCESS read-only
	STATUS current
	DESCRIPTION
		"The netmask for the administrative IP address on this machine. It is 
		 interpreted within the context of a sysAdminIpNetmaskType value."
	::= { sysAdminIpEntry 4 } 

sysAdminIpName OBJECT-TYPE 
	SYNTAX LongDisplayString
	MAX-ACCESS read-only
	STATUS current
	DESCRIPTION
		"The name of admin ip."
	::= { sysAdminIpEntry 5 } 

--==================================================================
-- Arp_static_entry
--==================================================================
sysArpStaticEntryNumber OBJECT-TYPE 
	SYNTAX INTEGER
	MAX-ACCESS read-only
	STATUS current
	DESCRIPTION
		"The number of sysArpStaticEntry entries in the table."
	::= { sysArpStaticEntry 1 } 

sysArpStaticEntryTable OBJECT-TYPE
	SYNTAX SEQUENCE OF SysArpStaticEntryEntry
	MAX-ACCESS not-accessible
	STATUS current
	DESCRIPTION
		"A table containing information of static ARP/NDP entries."
	::= { sysArpStaticEntry 2 } 

sysArpStaticEntryEntry OBJECT-TYPE
	SYNTAX  SysArpStaticEntryEntry
	MAX-ACCESS not-accessible
	STATUS current
	DESCRIPTION
		"Columns in the sysArpStaticEntry Table"
	INDEX {
		sysArpStaticEntryName
	}
	::= { sysArpStaticEntryTable 1 } 

SysArpStaticEntryEntry ::= 
	SEQUENCE {
        	sysArpStaticEntryIpAddrType                            InetAddressType,
        	sysArpStaticEntryIpAddr                                InetAddress,
        	sysArpStaticEntryMacAddr                               MacAddress,
        	sysArpStaticEntryName                                  LongDisplayString
	}

sysArpStaticEntryIpAddrType OBJECT-TYPE 
	SYNTAX InetAddressType
	MAX-ACCESS read-only
	STATUS current
	DESCRIPTION
		"The IP address type of sysArpStaticEntryIpAddr."
	::= { sysArpStaticEntryEntry 1 } 

sysArpStaticEntryIpAddr OBJECT-TYPE 
	SYNTAX InetAddress
	MAX-ACCESS read-only
	STATUS current
	DESCRIPTION
		"An IP address entry of the ARP/NDP entry. It is interpreted within 
		the context of a sysArpStaticEntryIpAddrType."
	::= { sysArpStaticEntryEntry 2 } 

sysArpStaticEntryMacAddr OBJECT-TYPE 
	SYNTAX MacAddress
	MAX-ACCESS read-only
	STATUS current
	DESCRIPTION
		"The MAC address which the specified IP address to be mapped to."
	::= { sysArpStaticEntryEntry 3 } 

sysArpStaticEntryName OBJECT-TYPE 
	SYNTAX LongDisplayString
	MAX-ACCESS read-only
	STATUS current
	DESCRIPTION
		"The name binding"
	::= { sysArpStaticEntryEntry 4 } 

--==================================================================
-- Snmp_bridge_stat
--==================================================================
sysDot1dbaseStatResetStats OBJECT-TYPE 
	SYNTAX INTEGER
	MAX-ACCESS read-write
	STATUS current
	DESCRIPTION
		"The action to reset resetable statistics data in  sysDot1dbaseStat. 
		 Setting this value to 1 will reset statistics data. 
		 Note, some statistics data may not be reset including data that are incremental counters."
	::= { sysDot1dbaseStat 1 } 

sysDot1dbaseStatMacAddr OBJECT-TYPE 
	SYNTAX MacAddress
	MAX-ACCESS read-only
	STATUS current
	DESCRIPTION
		"The MAC address used by this bridge when it must
		be referred to in a unique fashion.   It is
		recommended that this be the numerically smallest
		MAC address of all ports that belong to this
		bridge.  However it is only required to be unique.
		When concatenated with dot1dStpPriority a unique
		bridge identifier is formed which is used in the
		spanning tree protocol."
	::= { sysDot1dbaseStat 2 } 

sysDot1dbaseStatNumPorts OBJECT-TYPE 
	SYNTAX INTEGER
	MAX-ACCESS read-only
	STATUS current
	DESCRIPTION
		"The number of ports controlled by this bridging entity."
	::= { sysDot1dbaseStat 3 } 

sysDot1dbaseStatType OBJECT-TYPE 
	SYNTAX INTEGER {
		uninitialized(0),
		unknown(1),
		transparentonly(2),
		sourcerouteonly(3)
	}
	MAX-ACCESS read-only
	STATUS current
	DESCRIPTION
		"Indicates what type of bridging this bridge can
		perform.  If a bridge is actually performing a
		certain type of bridging this will be indicated by
		entries in the port table for the given type."
	::= { sysDot1dbaseStat 4 } 

--==================================================================
-- Snmp_dot1dbase_stat_port
--==================================================================
sysDot1dbaseStatPortNumber OBJECT-TYPE 
	SYNTAX INTEGER
	MAX-ACCESS read-only
	STATUS current
	DESCRIPTION
		"The number of sysDot1dbaseStatPort entries in the table."
	::= { sysDot1dbaseStatPort 1 } 

sysDot1dbaseStatPortTable OBJECT-TYPE
	SYNTAX SEQUENCE OF SysDot1dbaseStatPortEntry
	MAX-ACCESS not-accessible
	STATUS current
	DESCRIPTION
		"A table that contains generic information about
		every port that is associated with this bridge.
		Transparent, source-route, etc. ports are included.
		This is a part of sysDot1dbaseStat and syssysDot1dbaseStatResetStat
		will reset data in this table."
	::= { sysDot1dbaseStatPort 2 } 

sysDot1dbaseStatPortEntry OBJECT-TYPE
	SYNTAX  SysDot1dbaseStatPortEntry
	MAX-ACCESS not-accessible
	STATUS current
	DESCRIPTION
		"Columns in the sysDot1dbaseStatPort Table"
	INDEX {
		sysDot1dbaseStatPortIndex
	}
	::= { sysDot1dbaseStatPortTable 1 } 

SysDot1dbaseStatPortEntry ::= 
	SEQUENCE {
        	sysDot1dbaseStatPortIndex                              INTEGER,
        	sysDot1dbaseStatPortPort                               INTEGER,
        	sysDot1dbaseStatPortName                               LongDisplayString,
        	sysDot1dbaseStatPortDelayExceededDiscards              Counter64,
        	sysDot1dbaseStatPortMtuExceededDiscards                Counter64
	}

sysDot1dbaseStatPortIndex OBJECT-TYPE 
	SYNTAX INTEGER(1..2147483647)
	MAX-ACCESS read-only
	STATUS current
	DESCRIPTION
		"The index of the table that contains generic information 
		about every port that is associated with this bridge."
	::= { sysDot1dbaseStatPortEntry 1 } 

sysDot1dbaseStatPortPort OBJECT-TYPE 
	SYNTAX INTEGER
	MAX-ACCESS read-only
	STATUS current
	DESCRIPTION
		"The port number of the port for which this entry
		contains bridge management information."
	::= { sysDot1dbaseStatPortEntry 2 } 

sysDot1dbaseStatPortName OBJECT-TYPE 
	SYNTAX LongDisplayString
	MAX-ACCESS read-only
	STATUS current
	DESCRIPTION
		"The name of the interface corresponding to the port."
	::= { sysDot1dbaseStatPortEntry 3 } 

sysDot1dbaseStatPortDelayExceededDiscards OBJECT-TYPE 
	SYNTAX Counter64
	MAX-ACCESS read-only
	STATUS current
	DESCRIPTION
		"The number of frames discarded by this port due
		to excessive transit delay through the bridge.  It
		is incremented by both transparent and source
		route bridges."
	::= { sysDot1dbaseStatPortEntry 4 } 

sysDot1dbaseStatPortMtuExceededDiscards OBJECT-TYPE 
	SYNTAX Counter64
	MAX-ACCESS read-only
	STATUS current
	DESCRIPTION
		"The number of frames discarded by this port due
		to an excessive size.  It is incremented by both
		transparent and source route bridges."
	::= { sysDot1dbaseStatPortEntry 5 } 

--==================================================================
-- Interface
--==================================================================
sysInterfaceNumber OBJECT-TYPE 
	SYNTAX INTEGER
	MAX-ACCESS read-only
	STATUS current
	DESCRIPTION
		"The number of sysInterface entries in the table."
	::= { sysInterface 1 } 

sysInterfaceTable OBJECT-TYPE
	SYNTAX SEQUENCE OF SysInterfaceEntry
	MAX-ACCESS not-accessible
	STATUS current
	DESCRIPTION
		"A table containing information of the interfaces on the device."
	::= { sysInterface 2 } 

sysInterfaceEntry OBJECT-TYPE
	SYNTAX  SysInterfaceEntry
	MAX-ACCESS not-accessible
	STATUS current
	DESCRIPTION
		"Columns in the sysInterface Table"
	INDEX {
		sysInterfaceName
	}
	::= { sysInterfaceTable 1 } 

SysInterfaceEntry ::= 
	SEQUENCE {
        	sysInterfaceName                                       LongDisplayString,
        	sysInterfaceMediaMaxSpeed                              Integer32,
        	sysInterfaceMediaMaxDuplex                             INTEGER,
        	sysInterfaceMediaActiveSpeed                           Integer32,
        	sysInterfaceMediaActiveDuplex                          INTEGER,
        	sysInterfaceMacAddr                                    MacAddress,
        	sysInterfaceMtu                                        Integer32,
        	sysInterfaceEnabled                                    INTEGER,
        	sysInterfaceLearnMode                                  INTEGER,
        	sysInterfaceFlowCtrlReq                                INTEGER,
        	sysInterfaceStpLink                                    INTEGER,
        	sysInterfaceStpEdge                                    INTEGER,
        	sysInterfaceStpEdgeActive                              INTEGER,
        	sysInterfaceStpAuto                                    INTEGER,
        	sysInterfaceStpEnable                                  INTEGER,
        	sysInterfaceStpReset                                   INTEGER,
        	sysInterfaceStatus                                     INTEGER,
        	sysInterfaceComboPort                                  INTEGER,
        	sysInterfacePreferSfp                                  INTEGER,
        	sysInterfaceSfpMedia                                   INTEGER,
        	sysInterfacePhyMaster                                  INTEGER
	}

sysInterfaceName OBJECT-TYPE 
	SYNTAX LongDisplayString
	MAX-ACCESS read-only
	STATUS current
	DESCRIPTION
		"The name of an interface."
	::= { sysInterfaceEntry 1 } 

sysInterfaceMediaMaxSpeed OBJECT-TYPE 
	SYNTAX Integer32
	MAX-ACCESS read-only
	STATUS current
	DESCRIPTION
		"The best possible media speed in MBPS for the specified interface."
	::= { sysInterfaceEntry 2 } 

sysInterfaceMediaMaxDuplex OBJECT-TYPE 
	SYNTAX INTEGER {
		none(0),
		half(1),
		full(2)
	}
	MAX-ACCESS read-only
	STATUS current
	DESCRIPTION
		"The best possible media duplex mode for the specified interface.
		 half    - Force half duplex;
		 full    - Force full duplex;
		 none    - All media is deselected."
	::= { sysInterfaceEntry 3 } 

sysInterfaceMediaActiveSpeed OBJECT-TYPE 
	SYNTAX Integer32
	MAX-ACCESS read-only
	STATUS current
	DESCRIPTION
		"The current active media speed for the specified interface."
	::= { sysInterfaceEntry 4 } 

sysInterfaceMediaActiveDuplex OBJECT-TYPE 
	SYNTAX INTEGER {
		none(0),
		half(1),
		full(2)
	}
	MAX-ACCESS read-only
	STATUS current
	DESCRIPTION
		"The active media duplex mode for the specified interface.
		 half    - Force half duplex;
		 full    - Force full duplex;
		 none    - All media is deselected."
	::= { sysInterfaceEntry 5 } 

sysInterfaceMacAddr OBJECT-TYPE 
	SYNTAX MacAddress
	MAX-ACCESS read-only
	STATUS current
	DESCRIPTION
		"The MAC address of the specified interface."
	::= { sysInterfaceEntry 6 } 

sysInterfaceMtu OBJECT-TYPE 
	SYNTAX Integer32
	MAX-ACCESS read-only
	STATUS current
	DESCRIPTION
		"The maximum transmission unit size of datagram which can be 
		sent/received on the specified interface."
	::= { sysInterfaceEntry 7 } 

sysInterfaceEnabled OBJECT-TYPE 
	SYNTAX INTEGER {
		false(0),
		true(1)
	}
	MAX-ACCESS read-only
	STATUS current
	DESCRIPTION
		"The state of the specified interface, whether it is enabled."
	::= { sysInterfaceEntry 8 } 

sysInterfaceLearnMode OBJECT-TYPE 
	SYNTAX INTEGER {
		learnforward(0),
		nolearnforward(1),
		nolearndrop(2)
	}
	MAX-ACCESS read-only
	STATUS current
	DESCRIPTION
		"The learn mode of the specified interface."
	::= { sysInterfaceEntry 9 } 

sysInterfaceFlowCtrlReq OBJECT-TYPE 
	SYNTAX INTEGER {
		none(0),
		txrx(1),
		tx(2),
		rx(3)
	}
	MAX-ACCESS read-only
	STATUS current
	DESCRIPTION
		"The request pause state of the specified interface.
		none - no pause;
		txrx - pause all data flow;
		tx - pause out going data flow;
		rx - pause in coming data flow."
	::= { sysInterfaceEntry 10 } 

sysInterfaceStpLink OBJECT-TYPE 
	SYNTAX INTEGER {
		linkp2p(0),
		linkshared(1),
		linkauto(2)
	}
	MAX-ACCESS read-only
	STATUS current
	DESCRIPTION
		"The STP link types for the specified interface."
	::= { sysInterfaceEntry 11 } 

sysInterfaceStpEdge OBJECT-TYPE 
	SYNTAX INTEGER {
		false(0),
		true(1)
	}
	MAX-ACCESS read-only
	STATUS current
	DESCRIPTION
		"The edge-port state for the specified interface is enabled."
	::= { sysInterfaceEntry 12 } 

sysInterfaceStpEdgeActive OBJECT-TYPE 
	SYNTAX INTEGER {
		false(0),
		true(1)
	}
	MAX-ACCESS read-only
	STATUS current
	DESCRIPTION
		"The active edge-port state for the specified interface is enabled."
	::= { sysInterfaceEntry 13 } 

sysInterfaceStpAuto OBJECT-TYPE 
	SYNTAX INTEGER {
		false(0),
		true(1)
	}
	MAX-ACCESS read-only
	STATUS current
	DESCRIPTION
		"The auto edge-port detection state for the specified interface is enabled."
	::= { sysInterfaceEntry 14 } 

sysInterfaceStpEnable OBJECT-TYPE 
	SYNTAX INTEGER {
		false(0),
		true(1)
	}
	MAX-ACCESS read-only
	STATUS current
	DESCRIPTION
		"The STP state for the specified interface is enabled."
	::= { sysInterfaceEntry 15 } 

sysInterfaceStpReset OBJECT-TYPE 
	SYNTAX INTEGER {
		false(0),
		true(1)
	}
	MAX-ACCESS read-only
	STATUS current
	DESCRIPTION
		"The STP protocol detection reset state for the specified interface is enabled."
	::= { sysInterfaceEntry 16 } 

sysInterfaceStatus OBJECT-TYPE 
	SYNTAX INTEGER {
		up(0),
		down(1),
		uninitialized(3),
		unpopulated(5)
	}
	MAX-ACCESS read-only
	STATUS current
	DESCRIPTION
		"The current state of the specified interface.
		 up            - has link and is initialized;  
		 down          - has no link and is initialized;
		 uninitialized - has not been initialized;	
		 unpopulated   - interface not physically populated."
	::= { sysInterfaceEntry 17 } 

sysInterfaceComboPort OBJECT-TYPE 
	SYNTAX INTEGER {
		false(0),
		true(1)
	}
	MAX-ACCESS read-only
	STATUS current
	DESCRIPTION
		"The state which indicates whether or not the specified interface is a dual media 
		port supporting both fixed copper and SFP."
	::= { sysInterfaceEntry 18 } 

sysInterfacePreferSfp OBJECT-TYPE 
	SYNTAX INTEGER {
		false(0),
		true(1)
	}
	MAX-ACCESS read-only
	STATUS current
	DESCRIPTION
		"The state which indicates whether or not SFP is the preferred media. 
		This is only used only for dual media ports."
	::= { sysInterfaceEntry 19 } 

sysInterfaceSfpMedia OBJECT-TYPE 
	SYNTAX INTEGER {
		false(0),
		true(1)
	}
	MAX-ACCESS read-only
	STATUS current
	DESCRIPTION
		"The state indicating whether or not the specified interface supports SFP media."
	::= { sysInterfaceEntry 20 } 

sysInterfacePhyMaster OBJECT-TYPE 
	SYNTAX INTEGER {
		slave(0),
		master(1),
		auto(2),
		none(3)
	}
	MAX-ACCESS read-only
	STATUS current
	DESCRIPTION
		"The configured SFP media type of the specified interface."
	::= { sysInterfaceEntry 21 } 

--==================================================================
-- Interface_media_options
--==================================================================
sysIntfMediaNumber OBJECT-TYPE 
	SYNTAX INTEGER
	MAX-ACCESS read-only
	STATUS current
	DESCRIPTION
		"The number of sysInterfaceMediaOptions entries in the table."
	::= { sysInterfaceMediaOptions 1 } 

sysIntfMediaTable OBJECT-TYPE
	SYNTAX SEQUENCE OF SysIntfMediaEntry
	MAX-ACCESS not-accessible
	STATUS current
	DESCRIPTION
		"A table containing information of the non-SFP media options of the interfaces."
	::= { sysInterfaceMediaOptions 2 } 

sysIntfMediaEntry OBJECT-TYPE
	SYNTAX  SysIntfMediaEntry
	MAX-ACCESS not-accessible
	STATUS current
	DESCRIPTION
		"Columns in the sysIntfMedia Table"
	INDEX {
		sysIntfMediaName,
		sysIntfMediaIndex
	}
	::= { sysIntfMediaTable 1 } 

SysIntfMediaEntry ::= 
	SEQUENCE {
        	sysIntfMediaName                                       LongDisplayString,
        	sysIntfMediaIndex                                      INTEGER,
        	sysIntfMediaMediaOption                                INTEGER
	}

sysIntfMediaName OBJECT-TYPE 
	SYNTAX LongDisplayString
	MAX-ACCESS read-only
	STATUS current
	DESCRIPTION
		"The name of an interface."
	::= { sysIntfMediaEntry 1 } 

sysIntfMediaIndex OBJECT-TYPE 
	SYNTAX INTEGER(1..2147483647)
	MAX-ACCESS read-only
	STATUS current
	DESCRIPTION
		"The index of the non-SFP media option for the specified interface."
	::= { sysIntfMediaEntry 2 } 

sysIntfMediaMediaOption OBJECT-TYPE 
	SYNTAX INTEGER {
		media10THdx(1),
		media10TFdx(2),
		media100TxHdx(3),
		media100TxFdx(4),
		media1000THdx(5),
		media1000TFdx(6),
		media1000FxHdx(7),
		media1000FxFdx(8),
		media10000TxHdx(9),
		media10000TFdx(10),
		media10000FxHdx(11),
		media10000FxFdx(12),
		mediaAuto(13),
		mediaInternal(14),
		media1000SxHdx(15),
		media1000SxFdx(16),
		media1000LxHdx(17),
		media1000LxFdx(18),
		media10000SrFdx(19),
		media10000LrFdx(20),
		media10000ErFdx(21),
		media1000CxFdx(22),
		media10000SfpPlusCuFdx(23),
		media40000Sr4Fdx(24),
		media40000Lr4Fdx(25)
	}
	MAX-ACCESS read-only
	STATUS current
	DESCRIPTION
		"The media option for non-SFP media of the specified interface.
		media10THdx - 10BaseT:RJ45, half duplex,
		media10TFdx - 10BaseT:RJ45, full duplex,
		media100TxHdx - 100BaseTX:RJ45, half duplex,
		media100TxFdx - 100BaseTX:RJ45, full duplex,
		media1000THdx - 1000BaseT - gigabit ethernet RJ45, half duplex,
		media1000TFdx - 1000BaseTX:gigabit ethernet RJ45, full duplex,
		media1000FxHdx - deprecated. 1000BaseTX:gigabit over fiber, half duplex,
		media1000FxFdx - deprecated. 1000BaseTX:gigabit over fiber, full duplex,
		media10000TxHdx - deprecated. 1000BaseTX:10gigabit RJ45, half duplex,
		media10000TFdx - 10000BaseT - 10gig Ethernet - Copper, full duplex,
		media10000FxHdx - deprecated. 1000BaseTX:10gigabit over fiber, half duplex,
		media10000FxFdx - deprecated. 1000BaseTX:10gigabit over fiber, full duplex,
		mediaAuto - autoselect best media,
		mediaInternal - this media option is only used internally,
		media1000SxHdx - deprecated. 1000BaseSX: gigabit over fiber - Shortwave, half duplex,
		media1000SxFdx - 1000BaseSX: gigabit over fiber - Shortwave, full duplex ,
		media1000LxHdx - deprecated.1000BaseLX - gigabit over fiber - Longwave, full duplex,
		media1000LxFdx - 1000BaseLX - gigabit over fiber - Longwave, half duplex,
		media10000SrFdx - 10GBase-SR - Shortwave 850nm multimode fiber - 300m max - serial 64B/66B encoding, full duplex,
		media10000LrFdx - 10GBase-LR - Longwave 1310nm single mode fiber - 10km max - serial 64B/66B encoding, full duplex,
		media10000ErFdx - 10GBase-ER - Extra longwave 1550nm single mode fiber - 40km max - serial 64B/66B encoding, full duplex,
		media1000CxFdx - 1000BaseCX: Copper, full duplex,
		media10000SfpPlusCuFdx - 10G SFP+: Copper, full duplex,
		media40000Sr4Fdx - 40GBase: fiber, Shortwave (850nm), full duplex,
		media40000Lr4Fdx - 40GBase: fiber, Longwave (1310nm), full duplex."
	::= { sysIntfMediaEntry 3 } 

--==================================================================
-- Interface_id
--==================================================================
sysIfNumber OBJECT-TYPE 
	SYNTAX INTEGER
	MAX-ACCESS read-only
	STATUS current
	DESCRIPTION
		"The number of sysInterfaceId entries in the table."
	::= { sysInterfaceId 1 } 

sysIfTable OBJECT-TYPE
	SYNTAX SEQUENCE OF SysIfEntry
	MAX-ACCESS not-accessible
	STATUS current
	DESCRIPTION
		"A table that contains information of numerical IDs and names of a collection of 
			interfaces."
	::= { sysInterfaceId 2 } 

sysIfEntry OBJECT-TYPE
	SYNTAX  SysIfEntry
	MAX-ACCESS not-accessible
	STATUS current
	DESCRIPTION
		"Columns in the sysIf Table"
	INDEX {
		sysIfIndex
	}
	::= { sysIfTable 1 } 

SysIfEntry ::= 
	SEQUENCE {
        	sysIfIndex                                             INTEGER,
        	sysIfName                                              LongDisplayString
	}

sysIfIndex OBJECT-TYPE 
	SYNTAX INTEGER(1..2147483647)
	MAX-ACCESS read-only
	STATUS current
	DESCRIPTION
		"The unique value for an interface."
	::= { sysIfEntry 1 } 

sysIfName OBJECT-TYPE 
	SYNTAX LongDisplayString
	MAX-ACCESS read-only
	STATUS current
	DESCRIPTION
		"The name for an interface associated with the specified interface ID."
	::= { sysIfEntry 2 } 

--==================================================================
-- Interface_stat
--==================================================================
sysInterfaceStatResetStats OBJECT-TYPE 
	SYNTAX INTEGER
	MAX-ACCESS read-write
	STATUS current
	DESCRIPTION
		"The action to reset resetable statistics data in  sysInterfaceStat. 
		 Setting this value to 1 will reset statistics data. 
		 Note, some statistics data may not be reset including data that are incremental counters."
	::= { sysInterfaceStat 1 } 

sysInterfaceStatNumber OBJECT-TYPE 
	SYNTAX INTEGER
	MAX-ACCESS read-only
	STATUS current
	DESCRIPTION
		"The number of sysInterfaceStat entries in the table."
	::= { sysInterfaceStat 2 } 

sysInterfaceStatTable OBJECT-TYPE
	SYNTAX SEQUENCE OF SysInterfaceStatEntry
	MAX-ACCESS not-accessible
	STATUS current
	DESCRIPTION
		"A table containing statistic information of the interfaces on the device."
	::= { sysInterfaceStat 3 } 

sysInterfaceStatEntry OBJECT-TYPE
	SYNTAX  SysInterfaceStatEntry
	MAX-ACCESS not-accessible
	STATUS current
	DESCRIPTION
		"Columns in the sysInterfaceStat Table"
	INDEX {
		sysInterfaceStatName
	}
	::= { sysInterfaceStatTable 1 } 

SysInterfaceStatEntry ::= 
	SEQUENCE {
        	sysInterfaceStatName                                   LongDisplayString,
        	sysInterfaceStatPktsIn                                 Counter64,
        	sysInterfaceStatBytesIn                                Counter64,
        	sysInterfaceStatPktsOut                                Counter64,
        	sysInterfaceStatBytesOut                               Counter64,
        	sysInterfaceStatMcastIn                                Counter64,
        	sysInterfaceStatMcastOut                               Counter64,
        	sysInterfaceStatErrorsIn                               Counter64,
        	sysInterfaceStatErrorsOut                              Counter64,
        	sysInterfaceStatDropsIn                                Counter64,
        	sysInterfaceStatDropsOut                               Counter64,
        	sysInterfaceStatCollisions                             Counter64,
        	sysInterfaceStatPauseActive                            INTEGER
	}

sysInterfaceStatName OBJECT-TYPE 
	SYNTAX LongDisplayString
	MAX-ACCESS read-only
	STATUS current
	DESCRIPTION
		"The name of an interface."
	::= { sysInterfaceStatEntry 1 } 

sysInterfaceStatPktsIn OBJECT-TYPE 
	SYNTAX Counter64
	MAX-ACCESS read-only
	STATUS current
	DESCRIPTION
		"The number of packets received on this interface."
	::= { sysInterfaceStatEntry 2 } 

sysInterfaceStatBytesIn OBJECT-TYPE 
	SYNTAX Counter64
	MAX-ACCESS read-only
	STATUS current
	DESCRIPTION
		"The number of bytes received on the specified interface."
	::= { sysInterfaceStatEntry 3 } 

sysInterfaceStatPktsOut OBJECT-TYPE 
	SYNTAX Counter64
	MAX-ACCESS read-only
	STATUS current
	DESCRIPTION
		"The number of packets transmitted out of the specified interface."
	::= { sysInterfaceStatEntry 4 } 

sysInterfaceStatBytesOut OBJECT-TYPE 
	SYNTAX Counter64
	MAX-ACCESS read-only
	STATUS current
	DESCRIPTION
		"The number of bytes transmitted out of the specified interface."
	::= { sysInterfaceStatEntry 5 } 

sysInterfaceStatMcastIn OBJECT-TYPE 
	SYNTAX Counter64
	MAX-ACCESS read-only
	STATUS current
	DESCRIPTION
		"The number of multicast packets received on the specified interface."
	::= { sysInterfaceStatEntry 6 } 

sysInterfaceStatMcastOut OBJECT-TYPE 
	SYNTAX Counter64
	MAX-ACCESS read-only
	STATUS current
	DESCRIPTION
		"The number of multicast packets transmitted out of the specified interface."
	::= { sysInterfaceStatEntry 7 } 

sysInterfaceStatErrorsIn OBJECT-TYPE 
	SYNTAX Counter64
	MAX-ACCESS read-only
	STATUS current
	DESCRIPTION
		"The number of received packets that are either undersized, 
		oversized, or have FCS errors by the specified interface."
	::= { sysInterfaceStatEntry 8 } 

sysInterfaceStatErrorsOut OBJECT-TYPE 
	SYNTAX Counter64
	MAX-ACCESS read-only
	STATUS current
	DESCRIPTION
		"The number of excessive collisions, incremented for each 
		frame that experienced 16 collisions during transmission and 
		was aborted on the specified interface."
	::= { sysInterfaceStatEntry 9 } 

sysInterfaceStatDropsIn OBJECT-TYPE 
	SYNTAX Counter64
	MAX-ACCESS read-only
	STATUS current
	DESCRIPTION
		"The number of packets dropped on ingress for various reasons on the specified interface."
	::= { sysInterfaceStatEntry 10 } 

sysInterfaceStatDropsOut OBJECT-TYPE 
	SYNTAX Counter64
	MAX-ACCESS read-only
	STATUS current
	DESCRIPTION
		"The number of packets aged out or with excessive transmission 
		delays due to multiple deferrals on the specified interface."
	::= { sysInterfaceStatEntry 11 } 

sysInterfaceStatCollisions OBJECT-TYPE 
	SYNTAX Counter64
	MAX-ACCESS read-only
	STATUS current
	DESCRIPTION
		"The number of collisions on the specified interface, incremented by the 
		number of collisions experienced during transmissions of a frame"
	::= { sysInterfaceStatEntry 12 } 

sysInterfaceStatPauseActive OBJECT-TYPE 
	SYNTAX INTEGER {
		none(0),
		txrx(1),
		tx(2),
		rx(3)
	}
	MAX-ACCESS read-only
	STATUS current
	DESCRIPTION
		"The pause state of the specified interface.
		none - no pause;
		txrx - pause all data flow;
		tx - pause out going data flow;
		rx - pause in coming data flow."
	::= { sysInterfaceStatEntry 13 } 

--==================================================================
-- Snmp_ifx_stat
--==================================================================
sysIfxStatResetStats OBJECT-TYPE 
	SYNTAX INTEGER
	MAX-ACCESS read-write
	STATUS current
	DESCRIPTION
		"The action to reset resetable statistics data in  sysIfxStat. 
		 Setting this value to 1 will reset statistics data. 
		 Note, some statistics data may not be reset including data that are incremental counters."
	::= { sysIfxStat 1 } 

sysIfxStatNumber OBJECT-TYPE 
	SYNTAX INTEGER
	MAX-ACCESS read-only
	STATUS current
	DESCRIPTION
		"The number of sysIfxStat entries in the table."
	::= { sysIfxStat 2 } 

sysIfxStatTable OBJECT-TYPE
	SYNTAX SEQUENCE OF SysIfxStatEntry
	MAX-ACCESS not-accessible
	STATUS current
	DESCRIPTION
		"A table that contains additional statistic information of collection of 
		interfaces."
	::= { sysIfxStat 3 } 

sysIfxStatEntry OBJECT-TYPE
	SYNTAX  SysIfxStatEntry
	MAX-ACCESS not-accessible
	STATUS current
	DESCRIPTION
		"Columns in the sysIfxStat Table"
	INDEX {
		sysIfxStatName
	}
	::= { sysIfxStatTable 1 } 

SysIfxStatEntry ::= 
	SEQUENCE {
        	sysIfxStatName                                         LongDisplayString,
        	sysIfxStatInMulticastPkts                              Counter64,
        	sysIfxStatInBroadcastPkts                              Counter64,
        	sysIfxStatOutMulticastPkts                             Counter64,
        	sysIfxStatOutBroadcastPkts                             Counter64,
        	sysIfxStatHcInOctets                                   Counter64,
        	sysIfxStatHcInUcastPkts                                Counter64,
        	sysIfxStatHcInMulticastPkts                            Counter64,
        	sysIfxStatHcInBroadcastPkts                            Counter64,
        	sysIfxStatHcOutOctets                                  Counter64,
        	sysIfxStatHcOutUcastPkts                               Counter64,
        	sysIfxStatHcOutMulticastPkts                           Counter64,
        	sysIfxStatHcOutBroadcastPkts                           Counter64,
        	sysIfxStatHighSpeed                                    Counter64,
        	sysIfxStatConnectorPresent                             Integer32,
        	sysIfxStatCounterDiscontinuityTime                     Counter64,
        	sysIfxStatAlias                                        LongDisplayString
	}

sysIfxStatName OBJECT-TYPE 
	SYNTAX LongDisplayString
	MAX-ACCESS read-only
	STATUS current
	DESCRIPTION
		"The name of the interface."
	::= { sysIfxStatEntry 1 } 

sysIfxStatInMulticastPkts OBJECT-TYPE 
	SYNTAX Counter64
	MAX-ACCESS read-only
	STATUS current
	DESCRIPTION
		"The number of packets, delivered by this sub-layer to a
		higher (sub-)layer, which were addressed to a multicast
		address at this sub-layer.  For a MAC layer protocol, this
		includes both Group and Functional addresses."
	::= { sysIfxStatEntry 2 } 

sysIfxStatInBroadcastPkts OBJECT-TYPE 
	SYNTAX Counter64
	MAX-ACCESS read-only
	STATUS current
	DESCRIPTION
		"The number of packets, delivered by this sub-layer to a
		higher (sub-)layer, which were addressed to a broadcast
		address at this sub-layer."
	::= { sysIfxStatEntry 3 } 

sysIfxStatOutMulticastPkts OBJECT-TYPE 
	SYNTAX Counter64
	MAX-ACCESS read-only
	STATUS current
	DESCRIPTION
		"The total number of packets that higher-level protocols
		requested be transmitted, and which were addressed to a
		multicast address at this sub-layer, including those that
		were discarded or not sent.  For a MAC layer protocol, this
		includes both Group and Functional addresses."
	::= { sysIfxStatEntry 4 } 

sysIfxStatOutBroadcastPkts OBJECT-TYPE 
	SYNTAX Counter64
	MAX-ACCESS read-only
	STATUS current
	DESCRIPTION
		"The total number of packets that higher-level protocols
		requested be transmitted, and which were addressed to a
		broadcast address at this sub-layer, including those that
		were discarded or not sent."
	::= { sysIfxStatEntry 5 } 

sysIfxStatHcInOctets OBJECT-TYPE 
	SYNTAX Counter64
	MAX-ACCESS read-only
	STATUS current
	DESCRIPTION
		"The total number of octets received on the interface,
		including framing characters."
	::= { sysIfxStatEntry 6 } 

sysIfxStatHcInUcastPkts OBJECT-TYPE 
	SYNTAX Counter64
	MAX-ACCESS read-only
	STATUS current
	DESCRIPTION
		"The number of packets, delivered by this sub-layer to a
		higher (sub-)layer, which were not addressed to a multicast
		or broadcast address at this sub-layer."
	::= { sysIfxStatEntry 7 } 

sysIfxStatHcInMulticastPkts OBJECT-TYPE 
	SYNTAX Counter64
	MAX-ACCESS read-only
	STATUS current
	DESCRIPTION
		"The number of packets, delivered by this sub-layer to a
		higher (sub-)layer, which were addressed to a multicast
		address at this sub-layer.  For a MAC layer protocol, this
		includes both Group and Functional addresses."
	::= { sysIfxStatEntry 8 } 

sysIfxStatHcInBroadcastPkts OBJECT-TYPE 
	SYNTAX Counter64
	MAX-ACCESS read-only
	STATUS current
	DESCRIPTION
		"The number of packets, delivered by this sub-layer to a
		higher (sub-)layer, which were addressed to a broadcast
		address at this sub-layer."
	::= { sysIfxStatEntry 9 } 

sysIfxStatHcOutOctets OBJECT-TYPE 
	SYNTAX Counter64
	MAX-ACCESS read-only
	STATUS current
	DESCRIPTION
		"The total number of octets transmitted out of the
		interface, including framing characters."
	::= { sysIfxStatEntry 10 } 

sysIfxStatHcOutUcastPkts OBJECT-TYPE 
	SYNTAX Counter64
	MAX-ACCESS read-only
	STATUS current
	DESCRIPTION
		"The total number of packets that higher-level protocols
		requested be transmitted, and which were not addressed to a
		multicast or broadcast address at this sub-layer, including
		those that were discarded or not sent."
	::= { sysIfxStatEntry 11 } 

sysIfxStatHcOutMulticastPkts OBJECT-TYPE 
	SYNTAX Counter64
	MAX-ACCESS read-only
	STATUS current
	DESCRIPTION
		"The total number of packets that higher-level protocols
		requested be transmitted, and which were addressed to a
		multicast address at this sub-layer, including those that
		were discarded or not sent.  For a MAC layer protocol, this
		includes both Group and Functional addresses."
	::= { sysIfxStatEntry 12 } 

sysIfxStatHcOutBroadcastPkts OBJECT-TYPE 
	SYNTAX Counter64
	MAX-ACCESS read-only
	STATUS current
	DESCRIPTION
		"The total number of packets that higher-level protocols
		requested be transmitted, and which were addressed to a
		broadcast address at this sub-layer, including those that
		were discarded or not sent."
	::= { sysIfxStatEntry 13 } 

sysIfxStatHighSpeed OBJECT-TYPE 
	SYNTAX Counter64
	MAX-ACCESS read-only
	STATUS current
	DESCRIPTION
		"An estimate of the interface's current bandwidth in units
		of 1,000,000 bits per second.  If this object reports a
		value of `n' then the speed of the interface is somewhere in
		the range of `n-500,000' to `n+499,999'.  For interfaces
		which do not vary in bandwidth or for those where no
		accurate estimation can be made, this object should contain
		the nominal bandwidth.  For a sub-layer which has no concept
		of bandwidth, this object should be zero."
	::= { sysIfxStatEntry 14 } 

sysIfxStatConnectorPresent OBJECT-TYPE 
	SYNTAX Integer32
	MAX-ACCESS read-only
	STATUS current
	DESCRIPTION
		"This object has the value 'true(1)' if the interface
		sublayer has a physical connector and the value 'false(2)'
		otherwise."
	::= { sysIfxStatEntry 15 } 

sysIfxStatCounterDiscontinuityTime OBJECT-TYPE 
	SYNTAX Counter64
	MAX-ACCESS read-only
	STATUS current
	DESCRIPTION
		"The value of sysUpTime on the most recent occasion at which
		any one or more of this interface's counters suffered a
		discontinuity.  The relevant counters are the specific
		instances associated with this interface of any Counter32 or
		Counter64 object contained in the sysInterfaceTable or sysInterfaceXTable. 
		If no such discontinuities have occurred since the last re-
		initialization of the local management subsystem, then this
		object contains a zero value."
	::= { sysIfxStatEntry 16 } 

sysIfxStatAlias OBJECT-TYPE 
	SYNTAX LongDisplayString
	MAX-ACCESS read-only
	STATUS current
	DESCRIPTION
		"This object is an 'alias' name for the interface as
		specified by a network manager, and provides a non-volatile
		'handle' for the interface."
	::= { sysIfxStatEntry 17 } 

--==================================================================
-- L2_forward
--==================================================================
sysL2ForwardNumber OBJECT-TYPE 
	SYNTAX INTEGER
	MAX-ACCESS read-only
	STATUS current
	DESCRIPTION
		"The number of sysL2Forward entries in the table."
	::= { sysL2Forward 1 } 

sysL2ForwardTable OBJECT-TYPE
	SYNTAX SEQUENCE OF SysL2ForwardEntry
	MAX-ACCESS not-accessible
	STATUS current
	DESCRIPTION
		"A table containing static L2 forwarding entries information."
	::= { sysL2Forward 2 } 

sysL2ForwardEntry OBJECT-TYPE
	SYNTAX  SysL2ForwardEntry
	MAX-ACCESS not-accessible
	STATUS current
	DESCRIPTION
		"Columns in the sysL2Forward Table"
	INDEX {
		sysL2ForwardVlanName,
		sysL2ForwardMacAddr
	}
	::= { sysL2ForwardTable 1 } 

SysL2ForwardEntry ::= 
	SEQUENCE {
        	sysL2ForwardVlanName                                   LongDisplayString,
        	sysL2ForwardMacAddr                                    MacAddress,
        	sysL2ForwardIfname                                     LongDisplayString,
        	sysL2ForwardIftype                                     INTEGER,
        	sysL2ForwardDynamic                                    INTEGER
	}

sysL2ForwardVlanName OBJECT-TYPE 
	SYNTAX LongDisplayString
	MAX-ACCESS read-only
	STATUS current
	DESCRIPTION
		"The VLAN name which static forward entity is from."
	::= { sysL2ForwardEntry 1 } 

sysL2ForwardMacAddr OBJECT-TYPE 
	SYNTAX MacAddress
	MAX-ACCESS read-only
	STATUS current
	DESCRIPTION
		"The MAC address for the specified VLAN."
	::= { sysL2ForwardEntry 2 } 

sysL2ForwardIfname OBJECT-TYPE 
	SYNTAX LongDisplayString
	MAX-ACCESS read-only
	STATUS current
	DESCRIPTION
		"The name of interface for the specified VLAN."
	::= { sysL2ForwardEntry 3 } 

sysL2ForwardIftype OBJECT-TYPE 
	SYNTAX INTEGER {
		interface(0),
		trunk(1)
	}
	MAX-ACCESS read-only
	STATUS current
	DESCRIPTION
		"The type of interface for the specified VLAN."
	::= { sysL2ForwardEntry 4 } 

sysL2ForwardDynamic OBJECT-TYPE 
	SYNTAX INTEGER {
		false(0),
		true(1)
	}
	MAX-ACCESS read-only
	STATUS current
	DESCRIPTION
		"The dynamic state of the specified entity."
	::= { sysL2ForwardEntry 5 } 

--==================================================================
-- Packet_filter_rule
--==================================================================
sysPacketFilterNumber OBJECT-TYPE 
	SYNTAX INTEGER
	MAX-ACCESS read-only
	STATUS current
	DESCRIPTION
		"The number of sysPacketFilter entries in the table."
	::= { sysPacketFilter 1 } 

sysPacketFilterTable OBJECT-TYPE
	SYNTAX SEQUENCE OF SysPacketFilterEntry
	MAX-ACCESS not-accessible
	STATUS current
	DESCRIPTION
		"A table containing information of packet filters."
	::= { sysPacketFilter 2 } 

sysPacketFilterEntry OBJECT-TYPE
	SYNTAX  SysPacketFilterEntry
	MAX-ACCESS not-accessible
	STATUS current
	DESCRIPTION
		"Columns in the sysPacketFilter Table"
	INDEX {
		sysPacketFilterRname
	}
	::= { sysPacketFilterTable 1 } 

SysPacketFilterEntry ::= 
	SEQUENCE {
        	sysPacketFilterRname                                   LongDisplayString,
        	sysPacketFilterOrder                                   INTEGER,
        	sysPacketFilterAction                                  INTEGER,
        	sysPacketFilterVname                                   LongDisplayString,
        	sysPacketFilterLog                                     INTEGER,
        	sysPacketFilterRclass                                  LongDisplayString,
        	sysPacketFilterExpression                              LongDisplayString
	}

sysPacketFilterRname OBJECT-TYPE 
	SYNTAX LongDisplayString
	MAX-ACCESS read-only
	STATUS current
	DESCRIPTION
		"The name of the rule is used only for identification by the 
		 user and for logging."
	::= { sysPacketFilterEntry 1 } 

sysPacketFilterOrder OBJECT-TYPE 
	SYNTAX INTEGER
	MAX-ACCESS read-only
	STATUS current
	DESCRIPTION
		"The rule sort-order. The sort-order part of the rule is an 
		 integer value used to assign a relative weight to the rule. 
		 The sort-order may be any number between 0 and 999, but no two 
		 rules may have the same value. The specific value of the 
		 sort-order is not important, only its position relative to the 
		 other rules' sort-orders.  Rule evaluation order is determined 
		 by starting with the lowest numbered rule and moving up through 
		 to the highest."
	::= { sysPacketFilterEntry 2 } 

sysPacketFilterAction OBJECT-TYPE 
	SYNTAX INTEGER {
		none(0),
		accept(1),
		discard(2),
		reject(3),
		continue(4)
	}
	MAX-ACCESS read-only
	STATUS current
	DESCRIPTION
		"The action the filter takes. The action part of the rule can 
		 be any one of the values accept, discard, reject or none.  
		 The reject behaves as discard, but also returns an ICMP packet 
		 to the sender indicating that the traffic matching the rule was 
		 explicitly rejected. The ICMP will be of type 3 (destination 
		 unreachable), code 13 (administratively prohibited), and 
		 contain most or all of the L3 and L4 headers of the packet 
		 being rejected.  The none is special in that it indicates no 
		 action. It can be used for pure accounting or logging purposes 
		 without making a decision on how to handle the traffic."
	::= { sysPacketFilterEntry 3 } 

sysPacketFilterVname OBJECT-TYPE 
	SYNTAX LongDisplayString
	MAX-ACCESS read-only
	STATUS current
	DESCRIPTION
		"The VLAN name currently in existence. The VLAN part of the  
		 rule determines which ingress VLAN to match on. If present,  
		 this must be a specific VLAN name currently in existence. If 
		 omitted, the rule matches all VLANs."
	::= { sysPacketFilterEntry 4 } 

sysPacketFilterLog OBJECT-TYPE 
	SYNTAX INTEGER {
		false(0),
		true(1)
	}
	MAX-ACCESS read-only
	STATUS current
	DESCRIPTION
		"The log option, whether or not logging will be performed. 
		 If a rule has an associated logging action, an entry will be 
		 created in the system log each time the rule is matched. The 
		 log entry will contain details of the traffic that matched 
		 the rule, such as source and destination addresses and ports. 
		 If a rule does not have an associated logging action, no log 
		 entry is created."
	::= { sysPacketFilterEntry 5 } 

sysPacketFilterRclass OBJECT-TYPE 
	SYNTAX LongDisplayString
	MAX-ACCESS read-only
	STATUS current
	DESCRIPTION
		"The rate class name specified by the user."
	::= { sysPacketFilterEntry 6 } 

sysPacketFilterExpression OBJECT-TYPE 
	SYNTAX LongDisplayString
	MAX-ACCESS read-only
	STATUS current
	DESCRIPTION
		"The BPF(Berkeley Packet Filter) filter expression. The filter
		 part of the rule is the expression used to match ingress 
		 traffic."
	::= { sysPacketFilterEntry 7 } 

--==================================================================
-- Packet_filter_allow_trusted_address
--==================================================================
sysPacketFilterAddrNumber OBJECT-TYPE 
	SYNTAX INTEGER
	MAX-ACCESS read-only
	STATUS current
	DESCRIPTION
		"The number of sysPacketFilterAddress entries in the table."
	::= { sysPacketFilterAddress 1 } 

sysPacketFilterAddrTable OBJECT-TYPE
	SYNTAX SEQUENCE OF SysPacketFilterAddrEntry
	MAX-ACCESS not-accessible
	STATUS current
	DESCRIPTION
		"A table containing information of rate filter allow/trusted addresses."
	::= { sysPacketFilterAddress 2 } 

sysPacketFilterAddrEntry OBJECT-TYPE
	SYNTAX  SysPacketFilterAddrEntry
	MAX-ACCESS not-accessible
	STATUS current
	DESCRIPTION
		"Columns in the sysPacketFilterAddr Table"
	INDEX {
		sysPacketFilterAddrRname,
		sysPacketFilterAddrIndex
	}
	::= { sysPacketFilterAddrTable 1 } 

SysPacketFilterAddrEntry ::= 
	SEQUENCE {
        	sysPacketFilterAddrIndex                               INTEGER,
        	sysPacketFilterAddrIpType                              InetAddressType,
        	sysPacketFilterAddrIp                                  InetAddress,
        	sysPacketFilterAddrRname                               LongDisplayString
	}

sysPacketFilterAddrIndex OBJECT-TYPE 
	SYNTAX INTEGER(1..2147483647)
	MAX-ACCESS read-only
	STATUS current
	DESCRIPTION
		"Name is now used for indexing."
	::= { sysPacketFilterAddrEntry 1 } 

sysPacketFilterAddrIpType OBJECT-TYPE 
	SYNTAX InetAddressType
	MAX-ACCESS read-only
	STATUS current
	DESCRIPTION
		"The IP address type of sysPacketFilterAllowTrustedAddress"
	::= { sysPacketFilterAddrEntry 2 } 

sysPacketFilterAddrIp OBJECT-TYPE 
	SYNTAX InetAddress
	MAX-ACCESS read-only
	STATUS current
	DESCRIPTION
		"The allow trusted IP address in the packet filter.  
		It is interpreted within the context of an  sysPacketFilterAllowTrustedAddressType value."
	::= { sysPacketFilterAddrEntry 3 } 

sysPacketFilterAddrRname OBJECT-TYPE 
	SYNTAX LongDisplayString
	MAX-ACCESS read-only
	STATUS current
	DESCRIPTION
		"The name of the rule for use in folders."
	::= { sysPacketFilterAddrEntry 4 } 

--==================================================================
-- Packet_filter_allow_trusted_vlan
--==================================================================
sysPacketFilterVlanNumber OBJECT-TYPE 
	SYNTAX INTEGER
	MAX-ACCESS read-only
	STATUS current
	DESCRIPTION
		"The number of sysPacketFilterVlan entries in the table."
	::= { sysPacketFilterVlan 1 } 

sysPacketFilterVlanTable OBJECT-TYPE
	SYNTAX SEQUENCE OF SysPacketFilterVlanEntry
	MAX-ACCESS not-accessible
	STATUS current
	DESCRIPTION
		"A table containing information of rate filter allow/trusted VLANs."
	::= { sysPacketFilterVlan 2 } 

sysPacketFilterVlanEntry OBJECT-TYPE
	SYNTAX  SysPacketFilterVlanEntry
	MAX-ACCESS not-accessible
	STATUS current
	DESCRIPTION
		"Columns in the sysPacketFilterVlan Table"
	INDEX {
		sysPacketFilterVlanRname,
		sysPacketFilterVlanIndex
	}
	::= { sysPacketFilterVlanTable 1 } 

SysPacketFilterVlanEntry ::= 
	SEQUENCE {
        	sysPacketFilterVlanIndex                               INTEGER,
        	sysPacketFilterVlanName                                LongDisplayString,
        	sysPacketFilterVlanRname                               LongDisplayString
	}

sysPacketFilterVlanIndex OBJECT-TYPE 
	SYNTAX INTEGER(1..2147483647)
	MAX-ACCESS read-only
	STATUS current
	DESCRIPTION
		"Name is now used for indexing."
	::= { sysPacketFilterVlanEntry 1 } 

sysPacketFilterVlanName OBJECT-TYPE 
	SYNTAX LongDisplayString
	MAX-ACCESS read-only
	STATUS current
	DESCRIPTION
		"The name of the allow trusted VLAN in the packet filter."
	::= { sysPacketFilterVlanEntry 2 } 

sysPacketFilterVlanRname OBJECT-TYPE 
	SYNTAX LongDisplayString
	MAX-ACCESS read-only
	STATUS current
	DESCRIPTION
		"The name of the rule for use in folders."
	::= { sysPacketFilterVlanEntry 3 } 

--==================================================================
-- Packet_filter_allow_trusted_mac_addr
--==================================================================
sysPacketFilterMacNumber OBJECT-TYPE 
	SYNTAX INTEGER
	MAX-ACCESS read-only
	STATUS current
	DESCRIPTION
		"The number of sysPacketFilterMac entries in the table."
	::= { sysPacketFilterMac 1 } 

sysPacketFilterMacTable OBJECT-TYPE
	SYNTAX SEQUENCE OF SysPacketFilterMacEntry
	MAX-ACCESS not-accessible
	STATUS current
	DESCRIPTION
		"A table containing information of rate filter allow/trusted MAC addresses."
	::= { sysPacketFilterMac 2 } 

sysPacketFilterMacEntry OBJECT-TYPE
	SYNTAX  SysPacketFilterMacEntry
	MAX-ACCESS not-accessible
	STATUS current
	DESCRIPTION
		"Columns in the sysPacketFilterMac Table"
	INDEX {
		sysPacketFilterMacRname,
		sysPacketFilterMacIndex
	}
	::= { sysPacketFilterMacTable 1 } 

SysPacketFilterMacEntry ::= 
	SEQUENCE {
        	sysPacketFilterMacIndex                                INTEGER,
        	sysPacketFilterMacAddr                                 MacAddress,
        	sysPacketFilterMacRname                                LongDisplayString
	}

sysPacketFilterMacIndex OBJECT-TYPE 
	SYNTAX INTEGER(1..2147483647)
	MAX-ACCESS read-only
	STATUS current
	DESCRIPTION
		"Name is now used for indexing."
	::= { sysPacketFilterMacEntry 1 } 

sysPacketFilterMacAddr OBJECT-TYPE 
	SYNTAX MacAddress
	MAX-ACCESS read-only
	STATUS current
	DESCRIPTION
		"The allow trusted MAC address in the packet filter."
	::= { sysPacketFilterMacEntry 2 } 

sysPacketFilterMacRname OBJECT-TYPE 
	SYNTAX LongDisplayString
	MAX-ACCESS read-only
	STATUS current
	DESCRIPTION
		"The name of the rule for use in folders."
	::= { sysPacketFilterMacEntry 3 } 

--==================================================================
-- Packet_filter_rule_stat
--==================================================================
sysPacketFilterStatResetStats OBJECT-TYPE 
	SYNTAX INTEGER
	MAX-ACCESS read-write
	STATUS current
	DESCRIPTION
		"The action to reset resetable statistics data in  sysPacketFilterStat. 
		 Setting this value to 1 will reset statistics data. 
		 Note, some statistics data may not be reset including data that are incremental counters."
	::= { sysPacketFilterStat 1 } 

sysPacketFilterStatNumber OBJECT-TYPE 
	SYNTAX INTEGER
	MAX-ACCESS read-only
	STATUS current
	DESCRIPTION
		"The number of sysPacketFilterStat entries in the table."
	::= { sysPacketFilterStat 2 } 

sysPacketFilterStatTable OBJECT-TYPE
	SYNTAX SEQUENCE OF SysPacketFilterStatEntry
	MAX-ACCESS not-accessible
	STATUS current
	DESCRIPTION
		"A table containing statistic information of packet filters."
	::= { sysPacketFilterStat 3 } 

sysPacketFilterStatEntry OBJECT-TYPE
	SYNTAX  SysPacketFilterStatEntry
	MAX-ACCESS not-accessible
	STATUS current
	DESCRIPTION
		"Columns in the sysPacketFilterStat Table"
	INDEX {
		sysPacketFilterStatRname
	}
	::= { sysPacketFilterStatTable 1 } 

SysPacketFilterStatEntry ::= 
	SEQUENCE {
        	sysPacketFilterStatRname                               LongDisplayString,
        	sysPacketFilterStatHits                                Counter64
	}

sysPacketFilterStatRname OBJECT-TYPE 
	SYNTAX LongDisplayString
	MAX-ACCESS read-only
	STATUS current
	DESCRIPTION
		"The name of the rule is used only for identification by the 
		 user and for logging."
	::= { sysPacketFilterStatEntry 1 } 

sysPacketFilterStatHits OBJECT-TYPE 
	SYNTAX Counter64
	MAX-ACCESS read-only
	STATUS current
	DESCRIPTION
		"The number of matches on filter rule. Each time a rule is 
		 matched by a packet, a use count for that rule is 
		 incremented. This is unrelated to the optional logging action 
		 which might be enabled for the rule. The use count for a new 
		 rule starts at zero and increments for each matching packet."
	::= { sysPacketFilterStatEntry 2 } 

--==================================================================
-- Route_mgmt_entry
--==================================================================
sysRouteMgmtEntryNumber OBJECT-TYPE 
	SYNTAX INTEGER
	MAX-ACCESS read-only
	STATUS current
	DESCRIPTION
		"The number of sysRouteMgmtEntry entries in the table."
	::= { sysRouteMgmtEntry 1 } 

sysRouteMgmtEntryTable OBJECT-TYPE
	SYNTAX SEQUENCE OF SysRouteMgmtEntryEntry
	MAX-ACCESS not-accessible
	STATUS current
	DESCRIPTION
		"A table containing administrative route information."
	::= { sysRouteMgmtEntry 2 } 

sysRouteMgmtEntryEntry OBJECT-TYPE
	SYNTAX  SysRouteMgmtEntryEntry
	MAX-ACCESS not-accessible
	STATUS current
	DESCRIPTION
		"Columns in the sysRouteMgmtEntry Table"
	INDEX {
		sysRouteMgmtEntryName
	}
	::= { sysRouteMgmtEntryTable 1 } 

SysRouteMgmtEntryEntry ::= 
	SEQUENCE {
        	sysRouteMgmtEntryDestType                              InetAddressType,
        	sysRouteMgmtEntryDest                                  InetAddress,
        	sysRouteMgmtEntryNetmaskType                           InetAddressType,
        	sysRouteMgmtEntryNetmask                               InetAddress,
        	sysRouteMgmtEntryType                                  INTEGER,
        	sysRouteMgmtEntryGatewayType                           InetAddressType,
        	sysRouteMgmtEntryGateway                               InetAddress,
        	sysRouteMgmtEntryMtu                                   INTEGER,
        	sysRouteMgmtEntryName                                  LongDisplayString
	}

sysRouteMgmtEntryDestType OBJECT-TYPE 
	SYNTAX InetAddressType
	MAX-ACCESS read-only
	STATUS current
	DESCRIPTION
		"The IP address type of sysRouteMgmtEntryDest."
	::= { sysRouteMgmtEntryEntry 1 } 

sysRouteMgmtEntryDest OBJECT-TYPE 
	SYNTAX InetAddress
	MAX-ACCESS read-only
	STATUS current
	DESCRIPTION
		"The destination IP address in the route table. It is interpreted 
		within the context of a sysRouteMgmtEntryDestType value."
	::= { sysRouteMgmtEntryEntry 2 } 

sysRouteMgmtEntryNetmaskType OBJECT-TYPE 
	SYNTAX InetAddressType
	MAX-ACCESS read-only
	STATUS current
	DESCRIPTION
		"The IP address type of sysRouteMgmtEntryNetmask."
	::= { sysRouteMgmtEntryEntry 3 } 

sysRouteMgmtEntryNetmask OBJECT-TYPE 
	SYNTAX InetAddress
	MAX-ACCESS read-only
	STATUS current
	DESCRIPTION
		"The netmask of the specified destination IP address in the route table.  
			It is interpreted within the context of 
		a sysRouteMgmtEntryNetmaskType value."
	::= { sysRouteMgmtEntryEntry 4 } 

sysRouteMgmtEntryType OBJECT-TYPE 
	SYNTAX INTEGER {
		gateway(0),
		pool(1),
		interface(2),
		blackhole(3)
	}
	MAX-ACCESS read-only
	STATUS current
	DESCRIPTION
		"The type of the specified route."
	::= { sysRouteMgmtEntryEntry 5 } 

sysRouteMgmtEntryGatewayType OBJECT-TYPE 
	SYNTAX InetAddressType
	MAX-ACCESS read-only
	STATUS current
	DESCRIPTION
		"The IP address type of sysRouteMgmtEntryGateway."
	::= { sysRouteMgmtEntryEntry 6 } 

sysRouteMgmtEntryGateway OBJECT-TYPE 
	SYNTAX InetAddress
	MAX-ACCESS read-only
	STATUS current
	DESCRIPTION
		"The gateway to the specified destination IP address in the route table. 
		It is interpreted within the context of an 
		sysRouteMgmtEntryGatewayType value."
	::= { sysRouteMgmtEntryEntry 7 } 

sysRouteMgmtEntryMtu OBJECT-TYPE 
	SYNTAX INTEGER
	MAX-ACCESS read-only
	STATUS current
	DESCRIPTION
		"The maximum transmission unit size of datagram which can be 
		sent to the specified destination."
	::= { sysRouteMgmtEntryEntry 8 } 

sysRouteMgmtEntryName OBJECT-TYPE 
	SYNTAX LongDisplayString
	MAX-ACCESS read-only
	STATUS current
	DESCRIPTION
		"The name of destination."
	::= { sysRouteMgmtEntryEntry 9 } 

--==================================================================
-- Route_static_entry
--==================================================================
sysRouteStaticEntryNumber OBJECT-TYPE 
	SYNTAX INTEGER
	MAX-ACCESS read-only
	STATUS current
	DESCRIPTION
		"The number of sysRouteStaticEntry entries in the table."
	::= { sysRouteStaticEntry 1 } 

sysRouteStaticEntryTable OBJECT-TYPE
	SYNTAX SEQUENCE OF SysRouteStaticEntryEntry
	MAX-ACCESS not-accessible
	STATUS current
	DESCRIPTION
		"A table containing static route information."
	::= { sysRouteStaticEntry 2 } 

sysRouteStaticEntryEntry OBJECT-TYPE
	SYNTAX  SysRouteStaticEntryEntry
	MAX-ACCESS not-accessible
	STATUS current
	DESCRIPTION
		"Columns in the sysRouteStaticEntry Table"
	INDEX {
		sysRouteStaticEntryName
	}
	::= { sysRouteStaticEntryTable 1 } 

SysRouteStaticEntryEntry ::= 
	SEQUENCE {
        	sysRouteStaticEntryDestType                            InetAddressType,
        	sysRouteStaticEntryDest                                InetAddress,
        	sysRouteStaticEntryNetmaskType                         InetAddressType,
        	sysRouteStaticEntryNetmask                             InetAddress,
        	sysRouteStaticEntryType                                INTEGER,
        	sysRouteStaticEntryVlanName                            LongDisplayString,
        	sysRouteStaticEntryGatewayType                         InetAddressType,
        	sysRouteStaticEntryGateway                             InetAddress,
        	sysRouteStaticEntryPoolName                            LongDisplayString,
        	sysRouteStaticEntryMtu                                 INTEGER,
        	sysRouteStaticEntryName                                LongDisplayString
	}

sysRouteStaticEntryDestType OBJECT-TYPE 
	SYNTAX InetAddressType
	MAX-ACCESS read-only
	STATUS current
	DESCRIPTION
		"The IP address type of sysRouteStaticEntryDest."
	::= { sysRouteStaticEntryEntry 1 } 

sysRouteStaticEntryDest OBJECT-TYPE 
	SYNTAX InetAddress
	MAX-ACCESS read-only
	STATUS current
	DESCRIPTION
		"The destination IP address in the route table. It is interpreted 
		within the context of a sysRouteStaticEntryDestType value."
	::= { sysRouteStaticEntryEntry 2 } 

sysRouteStaticEntryNetmaskType OBJECT-TYPE 
	SYNTAX InetAddressType
	MAX-ACCESS read-only
	STATUS current
	DESCRIPTION
		"The IP address type of sysRouteStaticEntryNetmask."
	::= { sysRouteStaticEntryEntry 3 } 

sysRouteStaticEntryNetmask OBJECT-TYPE 
	SYNTAX InetAddress
	MAX-ACCESS read-only
	STATUS current
	DESCRIPTION
		"The netmask of the specified destination IP address in the route table.  
			It is interpreted within the context of 
		a sysRouteStaticEntryNetmaskType value."
	::= { sysRouteStaticEntryEntry 4 } 

sysRouteStaticEntryType OBJECT-TYPE 
	SYNTAX INTEGER {
		gateway(0),
		pool(1),
		interface(2),
		blackhole(3)
	}
	MAX-ACCESS read-only
	STATUS current
	DESCRIPTION
		"The type of the specified route."
	::= { sysRouteStaticEntryEntry 5 } 

sysRouteStaticEntryVlanName OBJECT-TYPE 
	SYNTAX LongDisplayString
	MAX-ACCESS read-only
	STATUS current
	DESCRIPTION
		"The name of the VLAN which the specified destination associates with."
	::= { sysRouteStaticEntryEntry 6 } 

sysRouteStaticEntryGatewayType OBJECT-TYPE 
	SYNTAX InetAddressType
	MAX-ACCESS read-only
	STATUS current
	DESCRIPTION
		"The IP address type of sysRouteStaticEntryGateway."
	::= { sysRouteStaticEntryEntry 7 } 

sysRouteStaticEntryGateway OBJECT-TYPE 
	SYNTAX InetAddress
	MAX-ACCESS read-only
	STATUS current
	DESCRIPTION
		"The gateway to the specified destination IP address in the route table. 
		It is interpreted within the context of an 
		sysRouteStaticEntryGatewayType value."
	::= { sysRouteStaticEntryEntry 8 } 

sysRouteStaticEntryPoolName OBJECT-TYPE 
	SYNTAX LongDisplayString
	MAX-ACCESS read-only
	STATUS current
	DESCRIPTION
		"The name of the pool which the specified destination associates with."
	::= { sysRouteStaticEntryEntry 9 } 

sysRouteStaticEntryMtu OBJECT-TYPE 
	SYNTAX INTEGER
	MAX-ACCESS read-only
	STATUS current
	DESCRIPTION
		"The maximum transmission unit size of datagram which can be 
		sent to the specified destination."
	::= { sysRouteStaticEntryEntry 10 } 

sysRouteStaticEntryName OBJECT-TYPE 
	SYNTAX LongDisplayString
	MAX-ACCESS read-only
	STATUS current
	DESCRIPTION
		"The name of destination."
	::= { sysRouteStaticEntryEntry 11 } 

--==================================================================
-- Self_ip
--==================================================================
sysSelfIpNumber OBJECT-TYPE 
	SYNTAX INTEGER
	MAX-ACCESS read-only
	STATUS current
	DESCRIPTION
		"The number of sysSelfIp entries in the table."
	::= { sysSelfIp 1 } 

sysSelfIpTable OBJECT-TYPE
	SYNTAX SEQUENCE OF SysSelfIpEntry
	MAX-ACCESS not-accessible
	STATUS current
	DESCRIPTION
		"A table containing information of self IPs."
	::= { sysSelfIp 2 } 

sysSelfIpEntry OBJECT-TYPE
	SYNTAX  SysSelfIpEntry
	MAX-ACCESS not-accessible
	STATUS current
	DESCRIPTION
		"Columns in the sysSelfIp Table"
	INDEX {
		sysSelfIpName
	}
	::= { sysSelfIpTable 1 } 

SysSelfIpEntry ::= 
	SEQUENCE {
        	sysSelfIpAddrType                                      InetAddressType,
        	sysSelfIpAddr                                          InetAddress,
        	sysSelfIpNetmaskType                                   InetAddressType,
        	sysSelfIpNetmask                                       InetAddress,
        	sysSelfIpUnitId                                        Integer32,
        	sysSelfIpIsFloating                                    INTEGER,
        	sysSelfIpVlanName                                      LongDisplayString,
        	sysSelfIpName                                          LongDisplayString
	}

sysSelfIpAddrType OBJECT-TYPE 
	SYNTAX InetAddressType
	MAX-ACCESS read-only
	STATUS current
	DESCRIPTION
		"The IP address type of sysSelfIpAddr."
	::= { sysSelfIpEntry 1 } 

sysSelfIpAddr OBJECT-TYPE 
	SYNTAX InetAddress
	MAX-ACCESS read-only
	STATUS current
	DESCRIPTION
		"The IP address of a self IP. It is 
		 interpreted within the context of a sysSelfIpAddrType value."
	::= { sysSelfIpEntry 2 } 

sysSelfIpNetmaskType OBJECT-TYPE 
	SYNTAX InetAddressType
	MAX-ACCESS read-only
	STATUS current
	DESCRIPTION
		"The IP address type of sysSelfIpNetmask."
	::= { sysSelfIpEntry 3 } 

sysSelfIpNetmask OBJECT-TYPE 
	SYNTAX InetAddress
	MAX-ACCESS read-only
	STATUS current
	DESCRIPTION
		"The netmask of the specified self IP. It is interpreted within 
		 the context of a sysSelfIpNetmaskType value."
	::= { sysSelfIpEntry 4 } 

sysSelfIpUnitId OBJECT-TYPE 
	SYNTAX Integer32
	MAX-ACCESS read-only
	STATUS current
	DESCRIPTION
		"The unit number associated with the specified self IP address."
	::= { sysSelfIpEntry 5 } 

sysSelfIpIsFloating OBJECT-TYPE 
	SYNTAX INTEGER {
		false(0),
		true(1)
	}
	MAX-ACCESS read-only
	STATUS current
	DESCRIPTION
		"The state of the specified self IP address, whether it is shared."
	::= { sysSelfIpEntry 6 } 

sysSelfIpVlanName OBJECT-TYPE 
	SYNTAX LongDisplayString
	MAX-ACCESS read-only
	STATUS current
	DESCRIPTION
		"The VLAN associated with the specified self IP address."
	::= { sysSelfIpEntry 7 } 

sysSelfIpName OBJECT-TYPE 
	SYNTAX LongDisplayString
	MAX-ACCESS read-only
	STATUS current
	DESCRIPTION
		"The name of self IP."
	::= { sysSelfIpEntry 8 } 

--==================================================================
-- Self_port
--==================================================================
sysSelfPortNumber OBJECT-TYPE 
	SYNTAX INTEGER
	MAX-ACCESS read-only
	STATUS current
	DESCRIPTION
		"The number of sysSelfPort entries in the table."
	::= { sysSelfPort 1 } 

sysSelfPortTable OBJECT-TYPE
	SYNTAX SEQUENCE OF SysSelfPortEntry
	MAX-ACCESS not-accessible
	STATUS current
	DESCRIPTION
		"A table containing information of self IP access list."
	::= { sysSelfPort 2 } 

sysSelfPortEntry OBJECT-TYPE
	SYNTAX  SysSelfPortEntry
	MAX-ACCESS not-accessible
	STATUS current
	DESCRIPTION
		"Columns in the sysSelfPort Table"
	INDEX {
		sysSelfPortSelfName,
		sysSelfPortProtocol,
		sysSelfPortPort
	}
	::= { sysSelfPortTable 1 } 

SysSelfPortEntry ::= 
	SEQUENCE {
        	sysSelfPortAddrType                                    InetAddressType,
        	sysSelfPortAddr                                        InetAddress,
        	sysSelfPortProtocol                                    INTEGER,
        	sysSelfPortPort                                        InetPortNumber,
        	sysSelfPortSelfName                                    LongDisplayString
	}

sysSelfPortAddrType OBJECT-TYPE 
	SYNTAX InetAddressType
	MAX-ACCESS read-only
	STATUS	 deprecated
	DESCRIPTION
		"Deprecated!  Use self_name as index
		The IP address type of sysSelfPortAddr."
	::= { sysSelfPortEntry 1 } 

sysSelfPortAddr OBJECT-TYPE 
	SYNTAX InetAddress
	MAX-ACCESS read-only
	STATUS	 deprecated
	DESCRIPTION
		"Deprecated!  Use self_name as index
		The self IP address. 
		It is interpreted within the context of 
		a sysSelfPortAddrType value."
	::= { sysSelfPortEntry 2 } 

sysSelfPortProtocol OBJECT-TYPE 
	SYNTAX INTEGER(0..256)
	MAX-ACCESS read-only
	STATUS current
	DESCRIPTION
		"The protocol allowed to access for the specified self IP.
		'0' means allowing all protocols;
		'256' means allowing the default list, which is listed in sysSelfPortDefault."
	::= { sysSelfPortEntry 3 } 

sysSelfPortPort OBJECT-TYPE 
	SYNTAX InetPortNumber
	MAX-ACCESS read-only
	STATUS current
	DESCRIPTION
		"The service allowed to access for the specified self IP.
		'0' means allowing all services for the specified protocol(s)."
	::= { sysSelfPortEntry 4 } 

sysSelfPortSelfName OBJECT-TYPE 
	SYNTAX LongDisplayString
	MAX-ACCESS read-only
	STATUS current
	DESCRIPTION
		"The name of self port."
	::= { sysSelfPortEntry 5 } 

--==================================================================
-- Stp
--==================================================================
sysStpNumber OBJECT-TYPE 
	SYNTAX INTEGER
	MAX-ACCESS read-only
	STATUS current
	DESCRIPTION
		"The number of sysStp entries in the table."
	::= { sysStp 1 } 

sysStpTable OBJECT-TYPE
	SYNTAX SEQUENCE OF SysStpEntry
	MAX-ACCESS not-accessible
	STATUS current
	DESCRIPTION
		"A table containing information of STP instances of the BIGIP spanning tree."
	::= { sysStp 2 } 

sysStpEntry OBJECT-TYPE
	SYNTAX  SysStpEntry
	MAX-ACCESS not-accessible
	STATUS current
	DESCRIPTION
		"Columns in the sysStp Table"
	INDEX {
		sysStpName
	}
	::= { sysStpTable 1 } 

SysStpEntry ::= 
	SEQUENCE {
        	sysStpInstanceId                                       Integer32,
        	sysStpPriority                                         INTEGER,
        	sysStpRootAddr                                         MacAddress,
        	sysStpRegionalRootAddr                                 MacAddress,
        	sysStpName                                             LongDisplayString
	}

sysStpInstanceId OBJECT-TYPE 
	SYNTAX Integer32
	MAX-ACCESS read-only
	STATUS current
	DESCRIPTION
		" The spanning tree instance ID, 0-4095."
	::= { sysStpEntry 1 } 

sysStpPriority OBJECT-TYPE 
	SYNTAX INTEGER
	MAX-ACCESS read-only
	STATUS current
	DESCRIPTION
		"The bridge priority of the specified spanning tree instance.
		Each bridge in a spanning tree instance has a priority value, 
		which controls the topology of the spanning tree chosen by the protocol.
		The bridge with the lowest priority value will become the root 
		of the spanning tree. Priority values range from 0-61440 in steps 
		of 4096. Hence, the supported priorities are:
				   0       16384       32768       49152
				4096       20480       36864       53248
				8192       24576       40960       57344
			   12288       28672       45056       61440
		The default bridge priority is 61440, which will prevent BIGIP 
		from being chosen as the root bridge.  If the specified bridge 
		priority is not one of the allowed values listed above, it is
		rounded down to the next lower value in the list.
		In STP or RSTP mode, only STP instance 0 is valid."
	::= { sysStpEntry 2 } 

sysStpRootAddr OBJECT-TYPE 
	SYNTAX MacAddress
	MAX-ACCESS read-only
	STATUS current
	DESCRIPTION
		"The MAC address of the root bridge."
	::= { sysStpEntry 3 } 

sysStpRegionalRootAddr OBJECT-TYPE 
	SYNTAX MacAddress
	MAX-ACCESS read-only
	STATUS current
	DESCRIPTION
		"The MAC address of the regional root bridge."
	::= { sysStpEntry 4 } 

sysStpName OBJECT-TYPE 
	SYNTAX LongDisplayString
	MAX-ACCESS read-only
	STATUS current
	DESCRIPTION
		"STP name"
	::= { sysStpEntry 5 } 

--==================================================================
-- Stp_globals
--==================================================================
sysStpGlobalsMode OBJECT-TYPE 
	SYNTAX INTEGER {
		disable(0),
		stp(1),
		rstp(2),
		mstp(3),
		passthru(4)
	}
	MAX-ACCESS read-only
	STATUS	 deprecated
	DESCRIPTION
		"Deprecated!.
		The STP mode."
	::= { sysStpGlobals 1 } 

sysStpGlobalsFwdDelay OBJECT-TYPE 
	SYNTAX INTEGER
	MAX-ACCESS read-only
	STATUS	 deprecated
	DESCRIPTION
		"Deprecated!.
		The forward delay parameter, which controls how long an 
		interface was blocked from forwarding network traffic after 
		a reconfiguration of the spanning tree topology. The default 
		value is 15 seconds, and the valid range is 4-30 seconds.  
		Note that this parameter has no effect when the STP mode 
		is RSPT or MSTP, as long as all bridges in the spanning tree 
		use the RSTP or MSTP protocol."
	::= { sysStpGlobals 2 } 

sysStpGlobalsHelloTime OBJECT-TYPE 
	SYNTAX INTEGER
	MAX-ACCESS read-only
	STATUS	 deprecated
	DESCRIPTION
		"Deprecated!.
		The hello time, which is the time interval in seconds 
		between the periodic transmissions that communicate spanning 
		tree information to the adjacent bridges in the network. 
		The default value is 2 seconds, and the valid range is 1-10 seconds."
	::= { sysStpGlobals 3 } 

sysStpGlobalsMaxAge OBJECT-TYPE 
	SYNTAX INTEGER
	MAX-ACCESS read-only
	STATUS	 deprecated
	DESCRIPTION
		"Deprecated!.
		The maximum age parameter, which controls how long spanning tree 
		information received from other bridges is considered valid.  
		The default value is 20 seconds, and the valid range is 6-40 seconds."
	::= { sysStpGlobals 4 } 

sysStpGlobalsTransmitHold OBJECT-TYPE 
	SYNTAX INTEGER
	MAX-ACCESS read-only
	STATUS	 deprecated
	DESCRIPTION
		"Deprecated!.
		The transmit hold count parameter, which is an absolute limit on 
		the number of spanning tree protocol packets the BIG-IP may transmit 
		on a port in any hello time interval.  This ensures that the spanning 
		tree packets will not unduly load the network even in unstable 
		conditions. The default value is 6 packets, and the valid range 
		is 1-10 packets."
	::= { sysStpGlobals 5 } 

sysStpGlobalsMaxHops OBJECT-TYPE 
	SYNTAX INTEGER
	MAX-ACCESS read-only
	STATUS	 deprecated
	DESCRIPTION
		"Deprecated!.
		The maximum hops an MSTP packet may travel before it is discarded.  
		It's used only when the STP mode is MSTP."
	::= { sysStpGlobals 6 } 

sysStpGlobalsIdentifier OBJECT-TYPE 
	SYNTAX LongDisplayString
	MAX-ACCESS read-only
	STATUS	 deprecated
	DESCRIPTION
		"Deprecated!.
		The configuration identifier name in a spanning tree region, 
		used to identify a group of adjacent bridges with identical 
		configuration name, configuration revision levels, and assignments 
		of VLANs to spanning tree instances.  This setting is used only 
		when the STP mode is MSTP."
	::= { sysStpGlobals 7 } 

sysStpGlobalsRevision OBJECT-TYPE 
	SYNTAX INTEGER
	MAX-ACCESS read-only
	STATUS	 deprecated
	DESCRIPTION
		"Deprecated!.
		 The configuration revision level of the MSTP configuration.  
		It's used only when the STP mode is MSTP."
	::= { sysStpGlobals 8 } 

--==================================================================
-- Stp_interface_mbr
--==================================================================
sysStpInterfaceMbrNumber OBJECT-TYPE 
	SYNTAX INTEGER
	MAX-ACCESS read-only
	STATUS current
	DESCRIPTION
		"The number of sysStpInterfaceMbr entries in the table."
	::= { sysStpInterfaceMbr 1 } 

sysStpInterfaceMbrTable OBJECT-TYPE
	SYNTAX SEQUENCE OF SysStpInterfaceMbrEntry
	MAX-ACCESS not-accessible
	STATUS current
	DESCRIPTION
		"A table containing information of STP instances and their interfaces."
	::= { sysStpInterfaceMbr 2 } 

sysStpInterfaceMbrEntry OBJECT-TYPE
	SYNTAX  SysStpInterfaceMbrEntry
	MAX-ACCESS not-accessible
	STATUS current
	DESCRIPTION
		"Columns in the sysStpInterfaceMbr Table"
	INDEX {
		sysStpInterfaceMbrInstanceName,
		sysStpInterfaceMbrName
	}
	::= { sysStpInterfaceMbrTable 1 } 

SysStpInterfaceMbrEntry ::= 
	SEQUENCE {
        	sysStpInterfaceMbrInstanceId                           Integer32,
        	sysStpInterfaceMbrName                                 LongDisplayString,
        	sysStpInterfaceMbrType                                 INTEGER,
        	sysStpInterfaceMbrStateActive                          INTEGER,
        	sysStpInterfaceMbrRole                                 INTEGER,
        	sysStpInterfaceMbrPriority                             INTEGER,
        	sysStpInterfaceMbrPathCost                             Integer32,
        	sysStpInterfaceMbrStateRequested                       INTEGER,
        	sysStpInterfaceMbrInstanceName                         LongDisplayString
	}

sysStpInterfaceMbrInstanceId OBJECT-TYPE 
	SYNTAX Integer32
	MAX-ACCESS read-only
	STATUS	 deprecated
	DESCRIPTION
		"Deprecated! 
		A parent STP instance's ID."
	::= { sysStpInterfaceMbrEntry 1 } 

sysStpInterfaceMbrName OBJECT-TYPE 
	SYNTAX LongDisplayString
	MAX-ACCESS read-only
	STATUS current
	DESCRIPTION
		"The name of STP port object of the specified STP instance."
	::= { sysStpInterfaceMbrEntry 2 } 

sysStpInterfaceMbrType OBJECT-TYPE 
	SYNTAX INTEGER {
		interface(0),
		trunk(1)
	}
	MAX-ACCESS read-only
	STATUS current
	DESCRIPTION
		"The type of the STP port object of the associated STP instance."
	::= { sysStpInterfaceMbrEntry 3 } 

sysStpInterfaceMbrStateActive OBJECT-TYPE 
	SYNTAX INTEGER {
		detach(0),
		block(1),
		listen(2),
		learn(3),
		forward(4),
		disable(5)
	}
	MAX-ACCESS read-only
	STATUS current
	DESCRIPTION
		"The active state of the specified STP port object 
		in the associated STP instance."
	::= { sysStpInterfaceMbrEntry 4 } 

sysStpInterfaceMbrRole OBJECT-TYPE 
	SYNTAX INTEGER {
		disable(0),
		root(1),
		designate(2),
		alternate(3),
		backup(4),
		master(5)
	}
	MAX-ACCESS read-only
	STATUS current
	DESCRIPTION
		"The role of the specified STP port object in the associated STP instance."
	::= { sysStpInterfaceMbrEntry 5 } 

sysStpInterfaceMbrPriority OBJECT-TYPE 
	SYNTAX INTEGER
	MAX-ACCESS read-only
	STATUS current
	DESCRIPTION
		"The priority of the specified STP port object in the associated STP instance.
			 This priority value influences which STP port is chosen to carry 
		network traffic. Interfaces with numerically lower values are favored 
		to carry traffic. Interface priorities have values in the range
		from 0-240 in steps of 166. Hence, the supported priorities are:
				   0        64       128       192
				  16        80       144       208
				  32        96       160       224
				  48       112       176       240
		The default interface priority is 128.  If the specified interface 
		priority is not one of the allowed values listed above, 
		it is rounded down to the next lower value in the list.
		In STP or RSTP mode, only STP instance 0 is valid."
	::= { sysStpInterfaceMbrEntry 6 } 

sysStpInterfaceMbrPathCost OBJECT-TYPE 
	SYNTAX Integer32
	MAX-ACCESS read-only
	STATUS current
	DESCRIPTION
		"The path cost for the specified STP port object in the associated STP instance.
		An interface path cost represents the relative cost of sending network
		traffic through that interface. In calculating the spanning tree, 
		the algorithm tries to minimize the total path cost between each point
			and the root bridge. By manipulating the path costs of different 
		interfaces, it's possible to steer traffic toward paths that are faster,
		more reliable, and/or more economical. Path costs have a range of
		1-200,000,000, and the default path cost for an interface is based on 
		the interface's maximum speed (not the actual speed).
				  Max interface speed         Default path cost
					  10 Gb/s                 2,000
					   1 Gb/s                 20,000
					 100 Mb/s                 200,000
					  10 MB/s                 2,000,000
		The default path cost is a function of the interface's maximum speed, 
		not its actual speed, so the default path cost of a 10/100/1000 Mb/s 
		interface will be 20,000 even if the interface is running at 10 Mb/s.
		Changes in link speed don't cause path costs to change.
		Link aggregation doesn't affect the default path cost, 
		i.e. a trunk of four 1 Gb/s interfaces will still have a default path 
		cost of 20,000.
		In STP or RSTP mode, only STP instance 0 is valid."
	::= { sysStpInterfaceMbrEntry 7 } 

sysStpInterfaceMbrStateRequested OBJECT-TYPE 
	SYNTAX INTEGER {
		detach(0),
		block(1),
		listen(2),
		learn(3),
		forward(4),
		disable(5)
	}
	MAX-ACCESS read-only
	STATUS current
	DESCRIPTION
		"The requested state of the specified STP port object 
		in the associated STP instance."
	::= { sysStpInterfaceMbrEntry 8 } 

sysStpInterfaceMbrInstanceName OBJECT-TYPE 
	SYNTAX LongDisplayString
	MAX-ACCESS read-only
	STATUS current
	DESCRIPTION
		"Parent stp instance name"
	::= { sysStpInterfaceMbrEntry 9 } 

--==================================================================
-- Stp_vlan_mbr
--==================================================================
sysStpVlanMbrNumber OBJECT-TYPE 
	SYNTAX INTEGER
	MAX-ACCESS read-only
	STATUS current
	DESCRIPTION
		"The number of sysStpVlanMbr entries in the table."
	::= { sysStpVlanMbr 1 } 

sysStpVlanMbrTable OBJECT-TYPE
	SYNTAX SEQUENCE OF SysStpVlanMbrEntry
	MAX-ACCESS not-accessible
	STATUS current
	DESCRIPTION
		"A table containing information of STP instances and their VLAN members."
	::= { sysStpVlanMbr 2 } 

sysStpVlanMbrEntry OBJECT-TYPE
	SYNTAX  SysStpVlanMbrEntry
	MAX-ACCESS not-accessible
	STATUS current
	DESCRIPTION
		"Columns in the sysStpVlanMbr Table"
	INDEX {
		sysStpVlanMbrStpName,
		sysStpVlanMbrVlanVname
	}
	::= { sysStpVlanMbrTable 1 } 

SysStpVlanMbrEntry ::= 
	SEQUENCE {
        	sysStpVlanMbrInstanceId                                Integer32,
        	sysStpVlanMbrVlanVname                                 LongDisplayString,
        	sysStpVlanMbrStpName                                   LongDisplayString
	}

sysStpVlanMbrInstanceId OBJECT-TYPE 
	SYNTAX Integer32
	MAX-ACCESS read-only
	STATUS	 deprecated
	DESCRIPTION
		"Deprecated! 
		A parent STP instance's ID."
	::= { sysStpVlanMbrEntry 1 } 

sysStpVlanMbrVlanVname OBJECT-TYPE 
	SYNTAX LongDisplayString
	MAX-ACCESS read-only
	STATUS current
	DESCRIPTION
		"The name of a VLAN of the specified STP instance.
		This method may be used only in MSTP mode. In STP or RSTP mode, 
		all VLANs automatically belong to spanning tree instance 0."
	::= { sysStpVlanMbrEntry 2 } 

sysStpVlanMbrStpName OBJECT-TYPE 
	SYNTAX LongDisplayString
	MAX-ACCESS read-only
	STATUS current
	DESCRIPTION
		"Parent STP name"
	::= { sysStpVlanMbrEntry 3 } 

--==================================================================
-- Snmp_stp_bridge_stat
--==================================================================
sysStpBridgeStatResetStats OBJECT-TYPE 
	SYNTAX INTEGER
	MAX-ACCESS read-write
	STATUS current
	DESCRIPTION
		"The action to reset resetable statistics data in  sysStpBridgeStat. 
		 Setting this value to 1 will reset statistics data. 
		 Note, some statistics data may not be reset including data that are incremental counters."
	::= { sysStpBridgeStat 1 } 

sysStpBridgeStatMode OBJECT-TYPE 
	SYNTAX INTEGER {
		disable(0),
		stp(1),
		rstp(2),
		mstp(3),
		passthru(4)
	}
	MAX-ACCESS read-only
	STATUS current
	DESCRIPTION
		"The mode of STP bridge."
	::= { sysStpBridgeStat 2 } 

sysStpBridgeStatFwdDelay OBJECT-TYPE 
	SYNTAX INTEGER
	MAX-ACCESS read-only
	STATUS current
	DESCRIPTION
		"The forward delay in 256ths of a second.  
		It controls how fast a port changes its spanning state 
		when moving toward the Forwarding state. The value determines 
		how long the port stays in each of the Listening and Learning
		states, which precede the Forwarding state. This value is also used, 
		when a topology change has been detected and is underway, to age 
		all dynamic entries in the Forwarding Database. 
		[Note that this value is the one that this bridge is currently using, 
		in contrast to sysSnmpStpBridgeStatBridgeFwdDelay which is the value 
		that this bridge and all others would start using if/when this bridge 
		were to become the root."
	::= { sysStpBridgeStat 3 } 

sysStpBridgeStatHelloTime OBJECT-TYPE 
	SYNTAX INTEGER
	MAX-ACCESS read-only
	STATUS current
	DESCRIPTION
		"The hello time in 256ths of a second. It is the time interval 
		between the periodic transmissions that communicate spanning tree 
		information to the adjacent bridges in the network. This is 
		the actual value that this bridge is currently using."
	::= { sysStpBridgeStat 4 } 

sysStpBridgeStatMaxAge OBJECT-TYPE 
	SYNTAX INTEGER
	MAX-ACCESS read-only
	STATUS current
	DESCRIPTION
		"The maximum age in 256ths of a second. It controls how long 
		spanning tree information received from other bridges is 
		considered valid. This is the actual value that this bridge 
		is currently using."
	::= { sysStpBridgeStat 5 } 

sysStpBridgeStatBridgeFwdDelay OBJECT-TYPE 
	SYNTAX INTEGER
	MAX-ACCESS read-only
	STATUS current
	DESCRIPTION
		"The bridge forward time (256ths). The value that all bridges use 
		for ForwardDelay when this bridge is acting as the root."
	::= { sysStpBridgeStat 6 } 

sysStpBridgeStatBridgeHelloTime OBJECT-TYPE 
	SYNTAX INTEGER
	MAX-ACCESS read-only
	STATUS current
	DESCRIPTION
		"The bridge hello time (256ths). The value that all bridges use 
		for HelloTime when this bridge is acting as the root."
	::= { sysStpBridgeStat 7 } 

sysStpBridgeStatBridgeMaxAge OBJECT-TYPE 
	SYNTAX INTEGER
	MAX-ACCESS read-only
	STATUS current
	DESCRIPTION
		"The bridge maximum age (256ths). The value that all bridges use 
		for MaxAge when this bridge is acting as the root."
	::= { sysStpBridgeStat 8 } 

sysStpBridgeStatTransmitHold OBJECT-TYPE 
	SYNTAX INTEGER
	MAX-ACCESS read-only
	STATUS current
	DESCRIPTION
		"The transmit hold count in BPDUs (Bridge Protocol Data Units)  
		per hello time."
	::= { sysStpBridgeStat 9 } 

sysStpBridgeStatPathCost OBJECT-TYPE 
	SYNTAX Integer32
	MAX-ACCESS read-only
	STATUS current
	DESCRIPTION
		"CIST root bridge (external) path cost.
		CIST is Common and Internal Spanning Tree created by MSTP to represent 
		the connectivity of the entire network. This is equivalent to 
		the single spanning tree used for STP and RSTP. 
		Communications between MST regions occurs using the CIST"
	::= { sysStpBridgeStat 10 } 

sysStpBridgeStatRootPrio OBJECT-TYPE 
	SYNTAX INTEGER
	MAX-ACCESS read-only
	STATUS current
	DESCRIPTION
		"CIST root bridge priority. 
		CIST is Common and Internal Spanning Tree created by MSTP to represent
			the connectivity of the entire network. This is equivalent to
			the single spanning tree used for STP and RSTP.
			Communications between MST regions occurs using the CIST"
	::= { sysStpBridgeStat 11 } 

sysStpBridgeStatRootAddr OBJECT-TYPE 
	SYNTAX MacAddress
	MAX-ACCESS read-only
	STATUS current
	DESCRIPTION
		"CIST root bridge MAC address.
		CIST is Common and Internal Spanning Tree created by MSTP to represent
			the connectivity of the entire network. This is equivalent to
			the single spanning tree used for STP and RSTP.
			Communications between MST regions occurs using the CIST"
	::= { sysStpBridgeStat 12 } 

--==================================================================
-- Stp_bridge_tree_stat
--==================================================================
sysStpBridgeTreeStatNumber OBJECT-TYPE 
	SYNTAX INTEGER
	MAX-ACCESS read-only
	STATUS current
	DESCRIPTION
		"The number of sysStpBridgeTreeStat entries in the table."
	::= { sysStpBridgeTreeStat 1 } 

sysStpBridgeTreeStatTable OBJECT-TYPE
	SYNTAX SEQUENCE OF SysStpBridgeTreeStatEntry
	MAX-ACCESS not-accessible
	STATUS current
	DESCRIPTION
		"A table that contains port objects information of the BIGIP spanning tree.
		This is a part of sysStpBridgeStat and sysStpBrigeStatResetStat
		will reset data in this table."
	::= { sysStpBridgeTreeStat 2 } 

sysStpBridgeTreeStatEntry OBJECT-TYPE
	SYNTAX  SysStpBridgeTreeStatEntry
	MAX-ACCESS not-accessible
	STATUS current
	DESCRIPTION
		"Columns in the sysStpBridgeTreeStat Table"
	INDEX {
		sysStpBridgeTreeStatIndex
	}
	::= { sysStpBridgeTreeStatTable 1 } 

SysStpBridgeTreeStatEntry ::= 
	SEQUENCE {
        	sysStpBridgeTreeStatIndex                              INTEGER,
        	sysStpBridgeTreeStatInstanceId                         INTEGER,
        	sysStpBridgeTreeStatPriority                           INTEGER,
        	sysStpBridgeTreeStatLastTc                             TimeTicks,
        	sysStpBridgeTreeStatTcCount                            Integer32,
        	sysStpBridgeTreeStatDesigRootPrio                      INTEGER,
        	sysStpBridgeTreeStatDesigRootAddr                      MacAddress,
        	sysStpBridgeTreeStatInternalPathCost                   Integer32,
        	sysStpBridgeTreeStatRootPort                           LongDisplayString,
        	sysStpBridgeTreeStatRootPortNum                        INTEGER,
        	sysStpBridgeTreeStatInstanceName                       LongDisplayString
	}

sysStpBridgeTreeStatIndex OBJECT-TYPE 
	SYNTAX INTEGER(1..2147483647)
	MAX-ACCESS read-only
	STATUS current
	DESCRIPTION
		"The index of the table that contains generic information 
		about spanning bridge tree."
	::= { sysStpBridgeTreeStatEntry 1 } 

sysStpBridgeTreeStatInstanceId OBJECT-TYPE 
	SYNTAX INTEGER
	MAX-ACCESS read-only
	STATUS current
	DESCRIPTION
		"The spanning tree instance ID."
	::= { sysStpBridgeTreeStatEntry 2 } 

sysStpBridgeTreeStatPriority OBJECT-TYPE 
	SYNTAX INTEGER
	MAX-ACCESS read-only
	STATUS current
	DESCRIPTION
		"The bridge priority in the spanning tree."
	::= { sysStpBridgeTreeStatEntry 3 } 

sysStpBridgeTreeStatLastTc OBJECT-TYPE 
	SYNTAX TimeTicks
	MAX-ACCESS read-only
	STATUS current
	DESCRIPTION
		"The time of last topology change."
	::= { sysStpBridgeTreeStatEntry 4 } 

sysStpBridgeTreeStatTcCount OBJECT-TYPE 
	SYNTAX Integer32
	MAX-ACCESS read-only
	STATUS current
	DESCRIPTION
		"The count of topology changes."
	::= { sysStpBridgeTreeStatEntry 5 } 

sysStpBridgeTreeStatDesigRootPrio OBJECT-TYPE 
	SYNTAX INTEGER
	MAX-ACCESS read-only
	STATUS current
	DESCRIPTION
		"The regional root bridge priority (MSTP)."
	::= { sysStpBridgeTreeStatEntry 6 } 

sysStpBridgeTreeStatDesigRootAddr OBJECT-TYPE 
	SYNTAX MacAddress
	MAX-ACCESS read-only
	STATUS current
	DESCRIPTION
		"The regional root bridge address (MSTP)."
	::= { sysStpBridgeTreeStatEntry 7 } 

sysStpBridgeTreeStatInternalPathCost OBJECT-TYPE 
	SYNTAX Integer32
	MAX-ACCESS read-only
	STATUS current
	DESCRIPTION
		"The root internal path cost (MSTP)."
	::= { sysStpBridgeTreeStatEntry 8 } 

sysStpBridgeTreeStatRootPort OBJECT-TYPE 
	SYNTAX LongDisplayString
	MAX-ACCESS read-only
	STATUS current
	DESCRIPTION
		"The root port interface name"
	::= { sysStpBridgeTreeStatEntry 9 } 

sysStpBridgeTreeStatRootPortNum OBJECT-TYPE 
	SYNTAX INTEGER
	MAX-ACCESS read-only
	STATUS current
	DESCRIPTION
		"The root port number."
	::= { sysStpBridgeTreeStatEntry 10 } 

sysStpBridgeTreeStatInstanceName OBJECT-TYPE 
	SYNTAX LongDisplayString
	MAX-ACCESS read-only
	STATUS current
	DESCRIPTION
		"The spanning tree instance name."
	::= { sysStpBridgeTreeStatEntry 11 } 

--==================================================================
-- Snmp_stp_interface_stat
--==================================================================
sysStpInterfaceStatResetStats OBJECT-TYPE 
	SYNTAX INTEGER
	MAX-ACCESS read-write
	STATUS current
	DESCRIPTION
		"The action to reset resetable statistics data in  sysStpInterfaceStat. 
		 Setting this value to 1 will reset statistics data. 
		 Note, some statistics data may not be reset including data that are incremental counters."
	::= { sysStpInterfaceStat 1 } 

sysStpInterfaceStatNumber OBJECT-TYPE 
	SYNTAX INTEGER
	MAX-ACCESS read-only
	STATUS current
	DESCRIPTION
		"The number of sysStpInterfaceStat entries in the table."
	::= { sysStpInterfaceStat 2 } 

sysStpInterfaceStatTable OBJECT-TYPE
	SYNTAX SEQUENCE OF SysStpInterfaceStatEntry
	MAX-ACCESS not-accessible
	STATUS current
	DESCRIPTION
		"The spanning tree information apply to the  particular network 
		interfaces or trunks."
	::= { sysStpInterfaceStat 3 } 

sysStpInterfaceStatEntry OBJECT-TYPE
	SYNTAX  SysStpInterfaceStatEntry
	MAX-ACCESS not-accessible
	STATUS current
	DESCRIPTION
		"Columns in the sysStpInterfaceStat Table"
	INDEX {
		sysStpInterfaceStatName
	}
	::= { sysStpInterfaceStatTable 1 } 

SysStpInterfaceStatEntry ::= 
	SEQUENCE {
        	sysStpInterfaceStatName                                LongDisplayString,
        	sysStpInterfaceStatPortNum                             INTEGER,
        	sysStpInterfaceStatStpEnable                           INTEGER,
        	sysStpInterfaceStatPathCost                            Integer32,
        	sysStpInterfaceStatRootCost                            Integer32,
        	sysStpInterfaceStatRootPrio                            INTEGER,
        	sysStpInterfaceStatRootAddr                            MacAddress
	}

sysStpInterfaceStatName OBJECT-TYPE 
	SYNTAX LongDisplayString
	MAX-ACCESS read-only
	STATUS current
	DESCRIPTION
		"The name of an interface."
	::= { sysStpInterfaceStatEntry 1 } 

sysStpInterfaceStatPortNum OBJECT-TYPE 
	SYNTAX INTEGER
	MAX-ACCESS read-only
	STATUS current
	DESCRIPTION
		"The STP port number."
	::= { sysStpInterfaceStatEntry 2 } 

sysStpInterfaceStatStpEnable OBJECT-TYPE 
	SYNTAX INTEGER {
		false(0),
		true(1)
	}
	MAX-ACCESS read-only
	STATUS current
	DESCRIPTION
		"The state indicating whether STP is enable or not on port."
	::= { sysStpInterfaceStatEntry 3 } 

sysStpInterfaceStatPathCost OBJECT-TYPE 
	SYNTAX Integer32
	MAX-ACCESS read-only
	STATUS current
	DESCRIPTION
		"The external path cost of the specified port in the associated STP tree instance."
	::= { sysStpInterfaceStatEntry 4 } 

sysStpInterfaceStatRootCost OBJECT-TYPE 
	SYNTAX Integer32
	MAX-ACCESS read-only
	STATUS current
	DESCRIPTION
		"CIST (Common and Internal Spanning Tree in MSTP) root path cost."
	::= { sysStpInterfaceStatEntry 5 } 

sysStpInterfaceStatRootPrio OBJECT-TYPE 
	SYNTAX INTEGER
	MAX-ACCESS read-only
	STATUS current
	DESCRIPTION
		"CIST (Common and Internal Spanning Tree in MSTP) root bridge priority."
	::= { sysStpInterfaceStatEntry 6 } 

sysStpInterfaceStatRootAddr OBJECT-TYPE 
	SYNTAX MacAddress
	MAX-ACCESS read-only
	STATUS current
	DESCRIPTION
		"CIST (Common and Internal Spanning Tree in MSTP) root bridge MAC address."
	::= { sysStpInterfaceStatEntry 7 } 

--==================================================================
-- Stp_interface_tree_stat
--==================================================================
sysStpInterfaceTreeStatNumber OBJECT-TYPE 
	SYNTAX INTEGER
	MAX-ACCESS read-only
	STATUS current
	DESCRIPTION
		"The number of sysStpInterfaceTreeStat entries in the table."
	::= { sysStpInterfaceTreeStat 1 } 

sysStpInterfaceTreeStatTable OBJECT-TYPE
	SYNTAX SEQUENCE OF SysStpInterfaceTreeStatEntry
	MAX-ACCESS not-accessible
	STATUS current
	DESCRIPTION
		"A table that contains port objects information of the  spanning interface tree.
		This is a part of sysStpInterfaceStat and sysStpInterfaceStatResetStat
		will reset data in this table."
	::= { sysStpInterfaceTreeStat 2 } 

sysStpInterfaceTreeStatEntry OBJECT-TYPE
	SYNTAX  SysStpInterfaceTreeStatEntry
	MAX-ACCESS not-accessible
	STATUS current
	DESCRIPTION
		"Columns in the sysStpInterfaceTreeStat Table"
	INDEX {
		sysStpInterfaceTreeStatName,
		sysStpInterfaceTreeStatIndex
	}
	::= { sysStpInterfaceTreeStatTable 1 } 

SysStpInterfaceTreeStatEntry ::= 
	SEQUENCE {
        	sysStpInterfaceTreeStatName                            LongDisplayString,
        	sysStpInterfaceTreeStatIndex                           INTEGER,
        	sysStpInterfaceTreeStatInstanceId                      INTEGER,
        	sysStpInterfaceTreeStatPriority                        INTEGER,
        	sysStpInterfaceTreeStatState                           INTEGER,
        	sysStpInterfaceTreeStatStatRole                        INTEGER,
        	sysStpInterfaceTreeStatDesigRootPrio                   INTEGER,
        	sysStpInterfaceTreeStatDesigRootAddr                   MacAddress,
        	sysStpInterfaceTreeStatDesigCost                       Integer32,
        	sysStpInterfaceTreeStatDesigBridgePrio                 INTEGER,
        	sysStpInterfaceTreeStatDesigBridgeAddr                 MacAddress,
        	sysStpInterfaceTreeStatDesigPortNum                    INTEGER,
        	sysStpInterfaceTreeStatDesigPortPriority               INTEGER,
        	sysStpInterfaceTreeStatInternalPathCost                Integer32,
        	sysStpInterfaceTreeStatFwdTransitions                  Integer32
	}

sysStpInterfaceTreeStatName OBJECT-TYPE 
	SYNTAX LongDisplayString
	MAX-ACCESS read-only
	STATUS current
	DESCRIPTION
		"The name of an interface which represents a port object 
		in a spanning tree instance."
	::= { sysStpInterfaceTreeStatEntry 1 } 

sysStpInterfaceTreeStatIndex OBJECT-TYPE 
	SYNTAX INTEGER(1..2147483647)
	MAX-ACCESS read-only
	STATUS current
	DESCRIPTION
		"The index of the table that contains the information of 
		the specified port in a spanning tree instance."
	::= { sysStpInterfaceTreeStatEntry 2 } 

sysStpInterfaceTreeStatInstanceId OBJECT-TYPE 
	SYNTAX INTEGER
	MAX-ACCESS read-only
	STATUS current
	DESCRIPTION
		"The ID of the STP instance which the specified port associated with."
	::= { sysStpInterfaceTreeStatEntry 3 } 

sysStpInterfaceTreeStatPriority OBJECT-TYPE 
	SYNTAX INTEGER
	MAX-ACCESS read-only
	STATUS current
	DESCRIPTION
		"The priority of the specified port in the associated spanning tree instance."
	::= { sysStpInterfaceTreeStatEntry 4 } 

sysStpInterfaceTreeStatState OBJECT-TYPE 
	SYNTAX INTEGER {
		detach(0),
		block(1),
		listen(2),
		learn(3),
		forward(4),
		disable(5)
	}
	MAX-ACCESS read-only
	STATUS current
	DESCRIPTION
		"The state in which the specified port is in the associated spanning tree instance."
	::= { sysStpInterfaceTreeStatEntry 5 } 

sysStpInterfaceTreeStatStatRole OBJECT-TYPE 
	SYNTAX INTEGER {
		disable(0),
		root(1),
		designate(2),
		alternate(3),
		backup(4),
		master(5)
	}
	MAX-ACCESS read-only
	STATUS current
	DESCRIPTION
		"The role of the port object in the associated spanning tree instance."
	::= { sysStpInterfaceTreeStatEntry 6 } 

sysStpInterfaceTreeStatDesigRootPrio OBJECT-TYPE 
	SYNTAX INTEGER
	MAX-ACCESS read-only
	STATUS current
	DESCRIPTION
		"The regional root bridge priority component of the port's
		priority vector in the associated spanning tree instance."
	::= { sysStpInterfaceTreeStatEntry 7 } 

sysStpInterfaceTreeStatDesigRootAddr OBJECT-TYPE 
	SYNTAX MacAddress
	MAX-ACCESS read-only
	STATUS current
	DESCRIPTION
		"The regional root bridge MAC address component of the port's
		priority vector in the associated spanning tree instance."
	::= { sysStpInterfaceTreeStatEntry 8 } 

sysStpInterfaceTreeStatDesigCost OBJECT-TYPE 
	SYNTAX Integer32
	MAX-ACCESS read-only
	STATUS current
	DESCRIPTION
		"The internal root path cost component of the port's priority
		vector in the associated spanning tree instance."
	::= { sysStpInterfaceTreeStatEntry 9 } 

sysStpInterfaceTreeStatDesigBridgePrio OBJECT-TYPE 
	SYNTAX INTEGER
	MAX-ACCESS read-only
	STATUS current
	DESCRIPTION
		"The designated bridge priority component of the port's priority
		vector in the associated spanning tree instance."
	::= { sysStpInterfaceTreeStatEntry 10 } 

sysStpInterfaceTreeStatDesigBridgeAddr OBJECT-TYPE 
	SYNTAX MacAddress
	MAX-ACCESS read-only
	STATUS current
	DESCRIPTION
		"The designated bridge MAC address component of the port's
		priority vector in the associated spanning tree instance."
	::= { sysStpInterfaceTreeStatEntry 11 } 

sysStpInterfaceTreeStatDesigPortNum OBJECT-TYPE 
	SYNTAX INTEGER
	MAX-ACCESS read-only
	STATUS current
	DESCRIPTION
		"The designated port identifier component of the port's priority
		vector in the associated spanning tree instance."
	::= { sysStpInterfaceTreeStatEntry 12 } 

sysStpInterfaceTreeStatDesigPortPriority OBJECT-TYPE 
	SYNTAX INTEGER
	MAX-ACCESS read-only
	STATUS current
	DESCRIPTION
		"The designated port priority component of the port's priority
		vector in the associated spanning tree instance."
	::= { sysStpInterfaceTreeStatEntry 13 } 

sysStpInterfaceTreeStatInternalPathCost OBJECT-TYPE 
	SYNTAX Integer32
	MAX-ACCESS read-only
	STATUS current
	DESCRIPTION
		"The internal path cost of the specified port in the associated 
		spanning tree instance. This is only for MSTP."
	::= { sysStpInterfaceTreeStatEntry 14 } 

sysStpInterfaceTreeStatFwdTransitions OBJECT-TYPE 
	SYNTAX Integer32
	MAX-ACCESS read-only
	STATUS current
	DESCRIPTION
		"The count of transitions to forwarding state for the port 
		in the associated spanning tree instance."
	::= { sysStpInterfaceTreeStatEntry 15 } 

--==================================================================
-- Snmp_dot3_stat
--==================================================================
sysDot3StatResetStats OBJECT-TYPE 
	SYNTAX INTEGER
	MAX-ACCESS read-write
	STATUS current
	DESCRIPTION
		"The action to reset resetable statistics data in  sysDot3Stat. 
		 Setting this value to 1 will reset statistics data. 
		 Note, some statistics data may not be reset including data that are incremental counters."
	::= { sysDot3Stat 1 } 

sysDot3StatNumber OBJECT-TYPE 
	SYNTAX INTEGER
	MAX-ACCESS read-only
	STATUS current
	DESCRIPTION
		"The number of sysDot3Stat entries in the table."
	::= { sysDot3Stat 2 } 

sysDot3StatTable OBJECT-TYPE
	SYNTAX SEQUENCE OF SysDot3StatEntry
	MAX-ACCESS not-accessible
	STATUS current
	DESCRIPTION
		"A table that contains statistic information of collection of 
		ethernet-like interfaces attached to a particular system."
	::= { sysDot3Stat 3 } 

sysDot3StatEntry OBJECT-TYPE
	SYNTAX  SysDot3StatEntry
	MAX-ACCESS not-accessible
	STATUS current
	DESCRIPTION
		"Columns in the sysDot3Stat Table"
	INDEX {
		sysDot3StatName
	}
	::= { sysDot3StatTable 1 } 

SysDot3StatEntry ::= 
	SEQUENCE {
        	sysDot3StatName                                        LongDisplayString,
        	sysDot3StatAlignmentErrors                             Counter64,
        	sysDot3StatFcsErrors                                   Counter64,
        	sysDot3StatSingleCollisionFrames                       Counter64,
        	sysDot3StatMultiCollisionFrames                        Counter64,
        	sysDot3StatSqetestErrors                               Counter64,
        	sysDot3StatDeferredTx                                  Counter64,
        	sysDot3StatLateCollisions                              Counter64,
        	sysDot3StatExcessiveCollisions                         Counter64,
        	sysDot3StatIntmacTxErrors                              Counter64,
        	sysDot3StatCarrierSenseErrors                          Counter64,
        	sysDot3StatFrameTooLongs                               Counter64,
        	sysDot3StatIntmacRxErrors                              Counter64,
        	sysDot3StatSymbolErrors                                Counter64,
        	sysDot3StatDuplexStatus                                INTEGER,
        	sysDot3StatCollisionCount                              Counter64,
        	sysDot3StatCollisionFreq                               Counter64
	}

sysDot3StatName OBJECT-TYPE 
	SYNTAX LongDisplayString
	MAX-ACCESS read-only
	STATUS current
	DESCRIPTION
		"The name of the interface."
	::= { sysDot3StatEntry 1 } 

sysDot3StatAlignmentErrors OBJECT-TYPE 
	SYNTAX Counter64
	MAX-ACCESS read-only
	STATUS current
	DESCRIPTION
		"A count of frames received on a particular
		interface that are not an integral number of
		octets in length and do not pass the FCS check."
	::= { sysDot3StatEntry 2 } 

sysDot3StatFcsErrors OBJECT-TYPE 
	SYNTAX Counter64
	MAX-ACCESS read-only
	STATUS current
	DESCRIPTION
		"A count of frames received on a particular
		interface that are an integral number of octets
		in length but do not pass the FCS check.  This
		count does not include frames received with
		frame-too-long or frame-too-short error."
	::= { sysDot3StatEntry 3 } 

sysDot3StatSingleCollisionFrames OBJECT-TYPE 
	SYNTAX Counter64
	MAX-ACCESS read-only
	STATUS current
	DESCRIPTION
		"A count of successfully transmitted frames on
		a particular interface for which transmission
		is inhibited by exactly one collision."
	::= { sysDot3StatEntry 4 } 

sysDot3StatMultiCollisionFrames OBJECT-TYPE 
	SYNTAX Counter64
	MAX-ACCESS read-only
	STATUS current
	DESCRIPTION
		"A count of successfully transmitted frames on
		a particular interface for which transmission
		is inhibited by more than one collision."
	::= { sysDot3StatEntry 5 } 

sysDot3StatSqetestErrors OBJECT-TYPE 
	SYNTAX Counter64
	MAX-ACCESS read-only
	STATUS current
	DESCRIPTION
		"A count of times that the SQE TEST ERROR
		message is generated by the PLS sublayer for a
		particular interface. The SQE TEST ERROR
		is set in accordance with the rules for
		verification of the SQE detection mechanism in
		the PLS Carrier Sense Function as described in
		IEEE Std. 802.3, 1998 Edition, section 7.2.4.6."
	::= { sysDot3StatEntry 6 } 

sysDot3StatDeferredTx OBJECT-TYPE 
	SYNTAX Counter64
	MAX-ACCESS read-only
	STATUS current
	DESCRIPTION
		"A count of frames for which the first
		transmission attempt on a particular interface
		is delayed because the medium is busy.
		The count represented by an instance of this
		object does not include frames involved in
		collisions."
	::= { sysDot3StatEntry 7 } 

sysDot3StatLateCollisions OBJECT-TYPE 
	SYNTAX Counter64
	MAX-ACCESS read-only
	STATUS current
	DESCRIPTION
		"The number of times that a collision is
		detected on a particular interface later than
		one slotTime into the transmission of a packet."
	::= { sysDot3StatEntry 8 } 

sysDot3StatExcessiveCollisions OBJECT-TYPE 
	SYNTAX Counter64
	MAX-ACCESS read-only
	STATUS current
	DESCRIPTION
		"A count of frames for which transmission on a
		particular interface fails due to excessive
		collisions.
		This counter does not increment when the
		interface is operating in full-duplex mode."
	::= { sysDot3StatEntry 9 } 

sysDot3StatIntmacTxErrors OBJECT-TYPE 
	SYNTAX Counter64
	MAX-ACCESS read-only
	STATUS current
	DESCRIPTION
		"A count of frames for which transmission on a
		particular interface fails due to an internal
		MAC sublayer transmit error. A frame is only
		counted by an instance of this object if it is
		not counted by the corresponding instance of
		either the sysDot3StatLateCollisions object, the
		sysDot3StatExcessiveCollisions object, or the
		sysDot3StatCarrierSenseErrors object."
	::= { sysDot3StatEntry 10 } 

sysDot3StatCarrierSenseErrors OBJECT-TYPE 
	SYNTAX Counter64
	MAX-ACCESS read-only
	STATUS current
	DESCRIPTION
		"The number of times that the carrier sense
		condition was lost or never asserted when
		attempting to transmit a frame on a particular
		interface."
	::= { sysDot3StatEntry 11 } 

sysDot3StatFrameTooLongs OBJECT-TYPE 
	SYNTAX Counter64
	MAX-ACCESS read-only
	STATUS current
	DESCRIPTION
		"A count of frames received on a particular
		interface that exceed the maximum permitted
		frame size."
	::= { sysDot3StatEntry 12 } 

sysDot3StatIntmacRxErrors OBJECT-TYPE 
	SYNTAX Counter64
	MAX-ACCESS read-only
	STATUS current
	DESCRIPTION
		"A count of frames for which reception on a
		particular interface fails due to an internal
		MAC sublayer receive error. A frame is only
		counted by an instance of this object if it is
		not counted by the corresponding instance of
		either the sysDot3StatFrameTooLongs object, the
		sysDot3StatAlignmentErrors object, or the
		sysDot3StatFcsErrors object."
	::= { sysDot3StatEntry 13 } 

sysDot3StatSymbolErrors OBJECT-TYPE 
	SYNTAX Counter64
	MAX-ACCESS read-only
	STATUS current
	DESCRIPTION
		"This is a hardware counter that increments each time 
		a valid receiver was present and at least 1 invalid data 
		symbol was detected."
	::= { sysDot3StatEntry 14 } 

sysDot3StatDuplexStatus OBJECT-TYPE 
	SYNTAX INTEGER {
		unknown(1),
		halfDuplex(2),
		fullDuplex(3)
	}
	MAX-ACCESS read-only
	STATUS current
	DESCRIPTION
		"The current mode of operation of the MAC
		entity.  'unknown' indicates that the current
		duplex mode could not be determined."
	::= { sysDot3StatEntry 15 } 

sysDot3StatCollisionCount OBJECT-TYPE 
	SYNTAX Counter64
	MAX-ACCESS read-only
	STATUS current
	DESCRIPTION
		"The number of per-frame media collisions for
		which a particular collision histogram cell
		represents the frequency on a particular
		interface."
	::= { sysDot3StatEntry 16 } 

sysDot3StatCollisionFreq OBJECT-TYPE 
	SYNTAX Counter64
	MAX-ACCESS read-only
	STATUS current
	DESCRIPTION
		"A count of individual MAC frames for which the
		transmission (successful or otherwise) on a
		particular interface occurs after the
		frame has experienced exactly the number
		of collisions in the associated
		sysDot3CollisionCount object."
	::= { sysDot3StatEntry 17 } 

--==================================================================
-- Trunk
--==================================================================
sysTrunkNumber OBJECT-TYPE 
	SYNTAX INTEGER
	MAX-ACCESS read-only
	STATUS current
	DESCRIPTION
		"The number of sysTrunk entries in the table."
	::= { sysTrunk 1 } 

sysTrunkTable OBJECT-TYPE
	SYNTAX SEQUENCE OF SysTrunkEntry
	MAX-ACCESS not-accessible
	STATUS current
	DESCRIPTION
		"A table containing information of trunks."
	::= { sysTrunk 2 } 

sysTrunkEntry OBJECT-TYPE
	SYNTAX  SysTrunkEntry
	MAX-ACCESS not-accessible
	STATUS current
	DESCRIPTION
		"Columns in the sysTrunk Table"
	INDEX {
		sysTrunkName
	}
	::= { sysTrunkTable 1 } 

SysTrunkEntry ::= 
	SEQUENCE {
        	sysTrunkName                                           LongDisplayString,
        	sysTrunkStatus                                         INTEGER,
        	sysTrunkAggAddr                                        MacAddress,
        	sysTrunkCfgMbrCount                                    INTEGER,
        	sysTrunkOperBw                                         Integer32,
        	sysTrunkStpEnable                                      INTEGER,
        	sysTrunkStpReset                                       INTEGER,
        	sysTrunkLacpEnabled                                    INTEGER,
        	sysTrunkActiveLacp                                     INTEGER,
        	sysTrunkShortTimeout                                   INTEGER
	}

sysTrunkName OBJECT-TYPE 
	SYNTAX LongDisplayString
	MAX-ACCESS read-only
	STATUS current
	DESCRIPTION
		"The name of a trunk."
	::= { sysTrunkEntry 1 } 

sysTrunkStatus OBJECT-TYPE 
	SYNTAX INTEGER {
		up(0),
		down(1),
		disable(2),
		uninitialized(3),
		loopback(4),
		unpopulated(5)
	}
	MAX-ACCESS read-only
	STATUS current
	DESCRIPTION
		"The interface status."
	::= { sysTrunkEntry 2 } 

sysTrunkAggAddr OBJECT-TYPE 
	SYNTAX MacAddress
	MAX-ACCESS read-only
	STATUS current
	DESCRIPTION
		"The aggregator MAC address of the specified trunk."
	::= { sysTrunkEntry 3 } 

sysTrunkCfgMbrCount OBJECT-TYPE 
	SYNTAX INTEGER
	MAX-ACCESS read-only
	STATUS current
	DESCRIPTION
		"The number of configured members that the specified trunk has."
	::= { sysTrunkEntry 4 } 

sysTrunkOperBw OBJECT-TYPE 
	SYNTAX Integer32
	MAX-ACCESS read-only
	STATUS current
	DESCRIPTION
		"The operational bandwidth in Mbps."
	::= { sysTrunkEntry 5 } 

sysTrunkStpEnable OBJECT-TYPE 
	SYNTAX INTEGER {
		false(0),
		true(1)
	}
	MAX-ACCESS read-only
	STATUS current
	DESCRIPTION
		"Whether STP is enabled for the specified trunk."
	::= { sysTrunkEntry 6 } 

sysTrunkStpReset OBJECT-TYPE 
	SYNTAX INTEGER {
		false(0),
		true(1)
	}
	MAX-ACCESS read-only
	STATUS current
	DESCRIPTION
		"Whether STP reset command is enabled for the specified trunk."
	::= { sysTrunkEntry 7 } 

sysTrunkLacpEnabled OBJECT-TYPE 
	SYNTAX INTEGER {
		false(0),
		true(1)
	}
	MAX-ACCESS read-only
	STATUS current
	DESCRIPTION
		"Whether LACP is enabled for the specified trunk."
	::= { sysTrunkEntry 8 } 

sysTrunkActiveLacp OBJECT-TYPE 
	SYNTAX INTEGER {
		false(0),
		true(1)
	}
	MAX-ACCESS read-only
	STATUS current
	DESCRIPTION
		"The active versus passive LACP on the specified trunk."
	::= { sysTrunkEntry 9 } 

sysTrunkShortTimeout OBJECT-TYPE 
	SYNTAX INTEGER {
		false(0),
		true(1)
	}
	MAX-ACCESS read-only
	STATUS current
	DESCRIPTION
		"The short versus long timeout on the specified trunk."
	::= { sysTrunkEntry 10 } 

--==================================================================
-- Trunk_stat
--==================================================================
sysTrunkStatResetStats OBJECT-TYPE 
	SYNTAX INTEGER
	MAX-ACCESS read-write
	STATUS current
	DESCRIPTION
		"The action to reset resetable statistics data in  sysTrunkStat. 
		 Setting this value to 1 will reset statistics data. 
		 Note, some statistics data may not be reset including data that are incremental counters."
	::= { sysTrunkStat 1 } 

sysTrunkStatNumber OBJECT-TYPE 
	SYNTAX INTEGER
	MAX-ACCESS read-only
	STATUS current
	DESCRIPTION
		"The number of sysTrunkStat entries in the table."
	::= { sysTrunkStat 2 } 

sysTrunkStatTable OBJECT-TYPE
	SYNTAX SEQUENCE OF SysTrunkStatEntry
	MAX-ACCESS not-accessible
	STATUS current
	DESCRIPTION
		"A table containing statistic information of trunks."
	::= { sysTrunkStat 3 } 

sysTrunkStatEntry OBJECT-TYPE
	SYNTAX  SysTrunkStatEntry
	MAX-ACCESS not-accessible
	STATUS current
	DESCRIPTION
		"Columns in the sysTrunkStat Table"
	INDEX {
		sysTrunkStatName
	}
	::= { sysTrunkStatTable 1 } 

SysTrunkStatEntry ::= 
	SEQUENCE {
        	sysTrunkStatName                                       LongDisplayString,
        	sysTrunkStatPktsIn                                     Counter64,
        	sysTrunkStatBytesIn                                    Counter64,
        	sysTrunkStatPktsOut                                    Counter64,
        	sysTrunkStatBytesOut                                   Counter64,
        	sysTrunkStatMcastIn                                    Counter64,
        	sysTrunkStatMcastOut                                   Counter64,
        	sysTrunkStatErrorsIn                                   Counter64,
        	sysTrunkStatErrorsOut                                  Counter64,
        	sysTrunkStatDropsIn                                    Counter64,
        	sysTrunkStatDropsOut                                   Counter64,
        	sysTrunkStatCollisions                                 Counter64
	}

sysTrunkStatName OBJECT-TYPE 
	SYNTAX LongDisplayString
	MAX-ACCESS read-only
	STATUS current
	DESCRIPTION
		"The name of a trunk."
	::= { sysTrunkStatEntry 1 } 

sysTrunkStatPktsIn OBJECT-TYPE 
	SYNTAX Counter64
	MAX-ACCESS read-only
	STATUS current
	DESCRIPTION
		"The number of packets received on the specified trunk."
	::= { sysTrunkStatEntry 2 } 

sysTrunkStatBytesIn OBJECT-TYPE 
	SYNTAX Counter64
	MAX-ACCESS read-only
	STATUS current
	DESCRIPTION
		"The number of bytes received on the specified trunk."
	::= { sysTrunkStatEntry 3 } 

sysTrunkStatPktsOut OBJECT-TYPE 
	SYNTAX Counter64
	MAX-ACCESS read-only
	STATUS current
	DESCRIPTION
		"The number of packets transmitted out of the specified trunk."
	::= { sysTrunkStatEntry 4 } 

sysTrunkStatBytesOut OBJECT-TYPE 
	SYNTAX Counter64
	MAX-ACCESS read-only
	STATUS current
	DESCRIPTION
		"The number of bytes transmitted out of the specified trunk."
	::= { sysTrunkStatEntry 5 } 

sysTrunkStatMcastIn OBJECT-TYPE 
	SYNTAX Counter64
	MAX-ACCESS read-only
	STATUS current
	DESCRIPTION
		"The number of multicast packets received on the specified trunk."
	::= { sysTrunkStatEntry 6 } 

sysTrunkStatMcastOut OBJECT-TYPE 
	SYNTAX Counter64
	MAX-ACCESS read-only
	STATUS current
	DESCRIPTION
		"The number of multicast packets transmitted out of the specified trunk."
	::= { sysTrunkStatEntry 7 } 

sysTrunkStatErrorsIn OBJECT-TYPE 
	SYNTAX Counter64
	MAX-ACCESS read-only
	STATUS current
	DESCRIPTION
		"The number of received packets that are either undersized, 
		oversized, or have FCS errors by the specified trunk."
	::= { sysTrunkStatEntry 8 } 

sysTrunkStatErrorsOut OBJECT-TYPE 
	SYNTAX Counter64
	MAX-ACCESS read-only
	STATUS current
	DESCRIPTION
		"The number of excessive collisions, incremented for each 
		frame that experienced 16 collisions during transmission and 
		was aborted on the specified trunk."
	::= { sysTrunkStatEntry 9 } 

sysTrunkStatDropsIn OBJECT-TYPE 
	SYNTAX Counter64
	MAX-ACCESS read-only
	STATUS current
	DESCRIPTION
		"The number of packets dropped on ingress for various reasons on the specified trunk."
	::= { sysTrunkStatEntry 10 } 

sysTrunkStatDropsOut OBJECT-TYPE 
	SYNTAX Counter64
	MAX-ACCESS read-only
	STATUS current
	DESCRIPTION
		"The number of packets aged out or with excessive transmission 
		delays due to multiple deferrals on the specified trunk."
	::= { sysTrunkStatEntry 11 } 

sysTrunkStatCollisions OBJECT-TYPE 
	SYNTAX Counter64
	MAX-ACCESS read-only
	STATUS current
	DESCRIPTION
		"The number of collisions on the specified trunk, incremented by the 
		number of collisions experienced during transmissions of a frame"
	::= { sysTrunkStatEntry 12 } 

--==================================================================
-- Trunk_cfg_mbr
--==================================================================
sysTrunkCfgMemberNumber OBJECT-TYPE 
	SYNTAX INTEGER
	MAX-ACCESS read-only
	STATUS current
	DESCRIPTION
		"The number of sysTrunkCfgMember entries in the table."
	::= { sysTrunkCfgMember 1 } 

sysTrunkCfgMemberTable OBJECT-TYPE
	SYNTAX SEQUENCE OF SysTrunkCfgMemberEntry
	MAX-ACCESS not-accessible
	STATUS current
	DESCRIPTION
		"A table containing information of configured trunk members."
	::= { sysTrunkCfgMember 2 } 

sysTrunkCfgMemberEntry OBJECT-TYPE
	SYNTAX  SysTrunkCfgMemberEntry
	MAX-ACCESS not-accessible
	STATUS current
	DESCRIPTION
		"Columns in the sysTrunkCfgMember Table"
	INDEX {
		sysTrunkCfgMemberTrunkName,
		sysTrunkCfgMemberName
	}
	::= { sysTrunkCfgMemberTable 1 } 

SysTrunkCfgMemberEntry ::= 
	SEQUENCE {
        	sysTrunkCfgMemberTrunkName                             LongDisplayString,
        	sysTrunkCfgMemberName                                  LongDisplayString
	}

sysTrunkCfgMemberTrunkName OBJECT-TYPE 
	SYNTAX LongDisplayString
	MAX-ACCESS read-only
	STATUS current
	DESCRIPTION
		"The name of a trunk to which this member belongs."
	::= { sysTrunkCfgMemberEntry 1 } 

sysTrunkCfgMemberName OBJECT-TYPE 
	SYNTAX LongDisplayString
	MAX-ACCESS read-only
	STATUS current
	DESCRIPTION
		"The name of a trunk member associated with the specified trunk."
	::= { sysTrunkCfgMemberEntry 2 } 

--==================================================================
-- Vlan
--==================================================================
sysVlanNumber OBJECT-TYPE 
	SYNTAX INTEGER
	MAX-ACCESS read-only
	STATUS current
	DESCRIPTION
		"The number of sysVlan entries in the table."
	::= { sysVlan 1 } 

sysVlanTable OBJECT-TYPE
	SYNTAX SEQUENCE OF SysVlanEntry
	MAX-ACCESS not-accessible
	STATUS current
	DESCRIPTION
		"A table containing informations of VLANs."
	::= { sysVlan 2 } 

sysVlanEntry OBJECT-TYPE
	SYNTAX  SysVlanEntry
	MAX-ACCESS not-accessible
	STATUS current
	DESCRIPTION
		"Columns in the sysVlan Table"
	INDEX {
		sysVlanVname
	}
	::= { sysVlanTable 1 } 

SysVlanEntry ::= 
	SEQUENCE {
        	sysVlanVname                                           LongDisplayString,
        	sysVlanId                                              INTEGER,
        	sysVlanSpanningTree                                    INTEGER,
        	sysVlanMacMasquerade                                   MacAddress,
        	sysVlanMacTrue                                         MacAddress,
        	sysVlanSourceCheck                                     INTEGER,
        	sysVlanFailsafeEnabled                                 INTEGER,
        	sysVlanMtu                                             INTEGER,
        	sysVlanFailsafeTimeout                                 Integer32,
        	sysVlanFailsafeAction                                  INTEGER,
        	sysVlanMirrorHashPortEnable                            INTEGER,
        	sysVlanLearnMode                                       INTEGER
	}

sysVlanVname OBJECT-TYPE 
	SYNTAX LongDisplayString
	MAX-ACCESS read-only
	STATUS current
	DESCRIPTION
		"The name of a VLAN."
	::= { sysVlanEntry 1 } 

sysVlanId OBJECT-TYPE 
	SYNTAX INTEGER
	MAX-ACCESS read-only
	STATUS current
	DESCRIPTION
		"The VLAN tag numbers or IDs (valid range is 1-4095)."
	::= { sysVlanEntry 2 } 

sysVlanSpanningTree OBJECT-TYPE 
	SYNTAX INTEGER {
		false(0),
		true(1)
	}
	MAX-ACCESS read-only
	STATUS current
	DESCRIPTION
		"The status of spanning tree domain is enabled."
	::= { sysVlanEntry 3 } 

sysVlanMacMasquerade OBJECT-TYPE 
	SYNTAX MacAddress
	MAX-ACCESS read-only
	STATUS	 deprecated
	DESCRIPTION
		"Deprecated!  Use traffic group MAC address instead.
			The MAC masquerade address for the specified VLAN."
	::= { sysVlanEntry 4 } 

sysVlanMacTrue OBJECT-TYPE 
	SYNTAX MacAddress
	MAX-ACCESS read-only
	STATUS current
	DESCRIPTION
		"The true MAC address used by the specified VLAN."
	::= { sysVlanEntry 5 } 

sysVlanSourceCheck OBJECT-TYPE 
	SYNTAX INTEGER {
		false(0),
		true(1)
	}
	MAX-ACCESS read-only
	STATUS current
	DESCRIPTION
		"The source checking state for the specified VLAN. 
		If it's true and auto lasthop is disabled, check that the
		source of the first packet of a connection is correct 
		(correct VLAN, router, node)."
	::= { sysVlanEntry 6 } 

sysVlanFailsafeEnabled OBJECT-TYPE 
	SYNTAX INTEGER {
		false(0),
		true(1)
	}
	MAX-ACCESS read-only
	STATUS current
	DESCRIPTION
		"The failsafe state for the specified VLAN is enabled."
	::= { sysVlanEntry 7 } 

sysVlanMtu OBJECT-TYPE 
	SYNTAX INTEGER
	MAX-ACCESS read-only
	STATUS current
	DESCRIPTION
		"The maximum transmission unit size of datagram which can be 
			sent to the specified VLAN."
	::= { sysVlanEntry 8 } 

sysVlanFailsafeTimeout OBJECT-TYPE 
	SYNTAX Integer32
	MAX-ACCESS read-only
	STATUS current
	DESCRIPTION
		"The failsafe timeouts for the specified VLAN."
	::= { sysVlanEntry 9 } 

sysVlanFailsafeAction OBJECT-TYPE 
	SYNTAX INTEGER {
		unusedhaaction(0),
		reboot(1),
		restart(2),
		failover(3),
		goactive(4),
		noaction(5),
		restartall(6),
		failoveraborttm(7),
		gooffline(8),
		goofflinerestart(9),
		goofflineaborttm(10),
		goofflinedownlinks(11),
		goofflinedownlinksrestart(12)
	}
	MAX-ACCESS read-only
	STATUS current
	DESCRIPTION
		"The failsafe action for the specified VLAN."
	::= { sysVlanEntry 10 } 

sysVlanMirrorHashPortEnable OBJECT-TYPE 
	SYNTAX INTEGER {
		false(0),
		true(1)
	}
	MAX-ACCESS read-only
	STATUS current
	DESCRIPTION
		"The state whether to hash the port for VLAN mirroring for the specified VLAN."
	::= { sysVlanEntry 11 } 

sysVlanLearnMode OBJECT-TYPE 
	SYNTAX INTEGER {
		learnforward(0),
		nolearnforward(1),
		nolearndrop(2)
	}
	MAX-ACCESS read-only
	STATUS current
	DESCRIPTION
		"The learn mode of the specified VLAN."
	::= { sysVlanEntry 12 } 

--==================================================================
-- Vlan_member
--==================================================================
sysVlanMemberNumber OBJECT-TYPE 
	SYNTAX INTEGER
	MAX-ACCESS read-only
	STATUS current
	DESCRIPTION
		"The number of sysVlanMember entries in the table."
	::= { sysVlanMember 1 } 

sysVlanMemberTable OBJECT-TYPE
	SYNTAX SEQUENCE OF SysVlanMemberEntry
	MAX-ACCESS not-accessible
	STATUS current
	DESCRIPTION
		"A table containing information of VLAN members."
	::= { sysVlanMember 2 } 

sysVlanMemberEntry OBJECT-TYPE
	SYNTAX  SysVlanMemberEntry
	MAX-ACCESS not-accessible
	STATUS current
	DESCRIPTION
		"Columns in the sysVlanMember Table"
	INDEX {
		sysVlanMemberParentVname,
		sysVlanMemberVmname
	}
	::= { sysVlanMemberTable 1 } 

SysVlanMemberEntry ::= 
	SEQUENCE {
        	sysVlanMemberVmname                                    LongDisplayString,
        	sysVlanMemberParentVname                               LongDisplayString,
        	sysVlanMemberTagged                                    INTEGER,
        	sysVlanMemberType                                      INTEGER
	}

sysVlanMemberVmname OBJECT-TYPE 
	SYNTAX LongDisplayString
	MAX-ACCESS read-only
	STATUS current
	DESCRIPTION
		"The name of a VLAN member."
	::= { sysVlanMemberEntry 1 } 

sysVlanMemberParentVname OBJECT-TYPE 
	SYNTAX LongDisplayString
	MAX-ACCESS read-only
	STATUS current
	DESCRIPTION
		"The name of a VLAN to which the specified member belongs."
	::= { sysVlanMemberEntry 2 } 

sysVlanMemberTagged OBJECT-TYPE 
	SYNTAX INTEGER {
		false(0),
		true(1)
	}
	MAX-ACCESS read-only
	STATUS current
	DESCRIPTION
		"The tagged/untagged state of the specified VLAN member."
	::= { sysVlanMemberEntry 3 } 

sysVlanMemberType OBJECT-TYPE 
	SYNTAX INTEGER {
		interface(0),
		trunk(1)
	}
	MAX-ACCESS read-only
	STATUS current
	DESCRIPTION
		"The type of the specified VLAN member."
	::= { sysVlanMemberEntry 4 } 

--==================================================================
-- Vlangroup
--==================================================================
sysVlanGroupNumber OBJECT-TYPE 
	SYNTAX INTEGER
	MAX-ACCESS read-only
	STATUS current
	DESCRIPTION
		"The number of sysVlanGroup entries in the table."
	::= { sysVlanGroup 1 } 

sysVlanGroupTable OBJECT-TYPE
	SYNTAX SEQUENCE OF SysVlanGroupEntry
	MAX-ACCESS not-accessible
	STATUS current
	DESCRIPTION
		"A table containing information of VLAN groups."
	::= { sysVlanGroup 2 } 

sysVlanGroupEntry OBJECT-TYPE
	SYNTAX  SysVlanGroupEntry
	MAX-ACCESS not-accessible
	STATUS current
	DESCRIPTION
		"Columns in the sysVlanGroup Table"
	INDEX {
		sysVlanGroupName
	}
	::= { sysVlanGroupTable 1 } 

SysVlanGroupEntry ::= 
	SEQUENCE {
        	sysVlanGroupName                                       LongDisplayString,
        	sysVlanGroupVlanId                                     INTEGER,
        	sysVlanGroupMode                                       INTEGER,
        	sysVlanGroupBridgeAllTraffic                           INTEGER,
        	sysVlanGroupBridgeInStandby                            INTEGER,
        	sysVlanGroupBridgeMulticast                            INTEGER,
        	sysVlanGroupMacMasquerade                              MacAddress,
        	sysVlanGroupMacTrue                                    MacAddress
	}

sysVlanGroupName OBJECT-TYPE 
	SYNTAX LongDisplayString
	MAX-ACCESS read-only
	STATUS current
	DESCRIPTION
		"The name of a VLAN group."
	::= { sysVlanGroupEntry 1 } 

sysVlanGroupVlanId OBJECT-TYPE 
	SYNTAX INTEGER
	MAX-ACCESS read-only
	STATUS	 deprecated
	DESCRIPTION
		"Deprecated! The VLAN ID/tag numbers (valid range is 1-4095)."
	::= { sysVlanGroupEntry 2 } 

sysVlanGroupMode OBJECT-TYPE 
	SYNTAX INTEGER {
		transparent(0),
		translucent(1),
		opaque(2)
	}
	MAX-ACCESS read-only
	STATUS current
	DESCRIPTION
		"The transparency mode for the specified VLAN group. 
		transparent - bridge with no modifications;
		translucent - toggle locally-modified bit of src MAC;
		opaque - bridge using proxy-arp."
	::= { sysVlanGroupEntry 3 } 

sysVlanGroupBridgeAllTraffic OBJECT-TYPE 
	SYNTAX INTEGER {
		false(0),
		true(1)
	}
	MAX-ACCESS read-only
	STATUS current
	DESCRIPTION
		"The state to indicate whether to bridge non-IP traffic as 
		well as IP traffic for the specified VLAN group."
	::= { sysVlanGroupEntry 4 } 

sysVlanGroupBridgeInStandby OBJECT-TYPE 
	SYNTAX INTEGER {
		false(0),
		true(1)
	}
	MAX-ACCESS read-only
	STATUS current
	DESCRIPTION
		"The state to indicate whether to bridge while unit is 
		in standby mode for the specified VLAN group."
	::= { sysVlanGroupEntry 5 } 

sysVlanGroupBridgeMulticast OBJECT-TYPE 
	SYNTAX INTEGER {
		false(0),
		true(1)
	}
	MAX-ACCESS read-only
	STATUS current
	DESCRIPTION
		"The state to indicate whether to bridge multicast/broadcast 
		traffic for the specified VLAN group."
	::= { sysVlanGroupEntry 6 } 

sysVlanGroupMacMasquerade OBJECT-TYPE 
	SYNTAX MacAddress
	MAX-ACCESS read-only
	STATUS	 deprecated
	DESCRIPTION
		"Deprecated!  Use traffic group MAC address instead.
			The MAC masquerade address for the specified VLAN group."
	::= { sysVlanGroupEntry 7 } 

sysVlanGroupMacTrue OBJECT-TYPE 
	SYNTAX MacAddress
	MAX-ACCESS read-only
	STATUS current
	DESCRIPTION
		"The true MAC address used by the specified VLAN group."
	::= { sysVlanGroupEntry 8 } 

--==================================================================
-- Vlangroup_mbr
--==================================================================
sysVlanGroupMbrNumber OBJECT-TYPE 
	SYNTAX INTEGER
	MAX-ACCESS read-only
	STATUS current
	DESCRIPTION
		"The number of sysVlanGroupMbr entries in the table."
	::= { sysVlanGroupMbr 1 } 

sysVlanGroupMbrTable OBJECT-TYPE
	SYNTAX SEQUENCE OF SysVlanGroupMbrEntry
	MAX-ACCESS not-accessible
	STATUS current
	DESCRIPTION
		"A table containing information of VLAN group's members."
	::= { sysVlanGroupMbr 2 } 

sysVlanGroupMbrEntry OBJECT-TYPE
	SYNTAX  SysVlanGroupMbrEntry
	MAX-ACCESS not-accessible
	STATUS current
	DESCRIPTION
		"Columns in the sysVlanGroupMbr Table"
	INDEX {
		sysVlanGroupMbrGroupName,
		sysVlanGroupMbrVlanName
	}
	::= { sysVlanGroupMbrTable 1 } 

SysVlanGroupMbrEntry ::= 
	SEQUENCE {
        	sysVlanGroupMbrGroupName                               LongDisplayString,
        	sysVlanGroupMbrVlanName                                LongDisplayString
	}

sysVlanGroupMbrGroupName OBJECT-TYPE 
	SYNTAX LongDisplayString
	MAX-ACCESS read-only
	STATUS current
	DESCRIPTION
		"The name of a VLAN group."
	::= { sysVlanGroupMbrEntry 1 } 

sysVlanGroupMbrVlanName OBJECT-TYPE 
	SYNTAX LongDisplayString
	MAX-ACCESS read-only
	STATUS current
	DESCRIPTION
		"The name of a VLAN group's member associated with the specified VLAN group."
	::= { sysVlanGroupMbrEntry 2 } 

--==================================================================
-- Proxy_exclusion
--==================================================================
sysProxyExclusionNumber OBJECT-TYPE 
	SYNTAX INTEGER
	MAX-ACCESS read-only
	STATUS current
	DESCRIPTION
		"The number of sysProxyExclusion entries in the table."
	::= { sysProxyExclusion 1 } 

sysProxyExclusionTable OBJECT-TYPE
	SYNTAX SEQUENCE OF SysProxyExclusionEntry
	MAX-ACCESS not-accessible
	STATUS current
	DESCRIPTION
		"A table containing information of a list of IP's that proxy arp will ignore on VLAN groups."
	::= { sysProxyExclusion 2 } 

sysProxyExclusionEntry OBJECT-TYPE
	SYNTAX  SysProxyExclusionEntry
	MAX-ACCESS not-accessible
	STATUS current
	DESCRIPTION
		"Columns in the sysProxyExclusion Table"
	INDEX {
		sysProxyExclusionVlangroupName,
		sysProxyExclusionIpType,
		sysProxyExclusionIp
	}
	::= { sysProxyExclusionTable 1 } 

SysProxyExclusionEntry ::= 
	SEQUENCE {
        	sysProxyExclusionVlangroupName                         LongDisplayString,
        	sysProxyExclusionIpType                                InetAddressType,
        	sysProxyExclusionIp                                    InetAddress
	}

sysProxyExclusionVlangroupName OBJECT-TYPE 
	SYNTAX LongDisplayString
	MAX-ACCESS read-only
	STATUS current
	DESCRIPTION
		"The name of a VLAN group."
	::= { sysProxyExclusionEntry 1 } 

sysProxyExclusionIpType OBJECT-TYPE 
	SYNTAX InetAddressType
	MAX-ACCESS read-only
	STATUS current
	DESCRIPTION
		"The IP address type of sysProxyExclusionIp"
	::= { sysProxyExclusionEntry 2 } 

sysProxyExclusionIp OBJECT-TYPE 
	SYNTAX InetAddress
	MAX-ACCESS read-only
	STATUS current
	DESCRIPTION
		"The IP address ignored from the global proxy exclusion list 
		for the specified VLAN group. It is interpreted within the context 
		of a sysProxyExclusionIpType value"
	::= { sysProxyExclusionEntry 3 } 

--==================================================================
-- Cpu_status_stat
--==================================================================
sysCpuNumber OBJECT-TYPE 
	SYNTAX INTEGER
	MAX-ACCESS read-only
	STATUS	 deprecated
	DESCRIPTION
		"Deprecated!.
		The number of sysCpu entries in the table."
	::= { sysCpu 1 } 

sysCpuTable OBJECT-TYPE
	SYNTAX SEQUENCE OF SysCpuEntry
	MAX-ACCESS not-accessible
	STATUS deprecated
	DESCRIPTION
		"Deprecated! Replaced by sysCpuSensor table.
			A table containing information of CPU status on the system."
	::= { sysCpu 2 } 

sysCpuEntry OBJECT-TYPE
	SYNTAX  SysCpuEntry
	MAX-ACCESS not-accessible
	STATUS deprecated
	DESCRIPTION
		"Columns in the sysCpu Table"
	INDEX {
		sysCpuIndex
	}
	::= { sysCpuTable 1 } 

SysCpuEntry ::= 
	SEQUENCE {
        	sysCpuIndex                                            INTEGER,
        	sysCpuTemperature                                      INTEGER,
        	sysCpuFanSpeed                                         Integer32,
        	sysCpuName                                             LongDisplayString,
        	sysCpuSlot                                             INTEGER
	}

sysCpuIndex OBJECT-TYPE 
	SYNTAX INTEGER(1..2147483647)
	MAX-ACCESS read-only
	STATUS	 deprecated
	DESCRIPTION
		"Deprecated! Replaced by sysCpuSensor table.
			The CPU index on the system."
	::= { sysCpuEntry 1 } 

sysCpuTemperature OBJECT-TYPE 
	SYNTAX INTEGER
	MAX-ACCESS read-only
	STATUS	 deprecated
	DESCRIPTION
		"Deprecated! Replaced by sysCpuSensor table.
			The temperature of the indexed CPU on the system.
			This is only supported for the platform where
			the sensor data is available."
	::= { sysCpuEntry 2 } 

sysCpuFanSpeed OBJECT-TYPE 
	SYNTAX Integer32
	MAX-ACCESS read-only
	STATUS	 deprecated
	DESCRIPTION
		"Deprecated! Replaced by sysCpuSensor table.
			The fan speed (in RPM) of the indexed CPU on the system.,
			This is only supported for the platform where
			the sensor data is available."
	::= { sysCpuEntry 3 } 

sysCpuName OBJECT-TYPE 
	SYNTAX LongDisplayString
	MAX-ACCESS read-only
	STATUS	 deprecated
	DESCRIPTION
		"Deprecated! Replaced by sysCpuSensor table.
			Identifier for the CPU."
	::= { sysCpuEntry 4 } 

sysCpuSlot OBJECT-TYPE 
	SYNTAX INTEGER
	MAX-ACCESS read-only
	STATUS	 deprecated
	DESCRIPTION
		"Deprecated! Replaced by sysCpuSensor table.
			Chassis slot number, if applicable."
	::= { sysCpuEntry 5 } 

--==================================================================
-- Chassis_fan_status_stat
--==================================================================
sysChassisFanNumber OBJECT-TYPE 
	SYNTAX INTEGER
	MAX-ACCESS read-only
	STATUS current
	DESCRIPTION
		"The number of sysChassisFan entries in the table."
	::= { sysChassisFan 1 } 

sysChassisFanTable OBJECT-TYPE
	SYNTAX SEQUENCE OF SysChassisFanEntry
	MAX-ACCESS not-accessible
	STATUS current
	DESCRIPTION
		"A table containing information of chassis fan status of the system."
	::= { sysChassisFan 2 } 

sysChassisFanEntry OBJECT-TYPE
	SYNTAX  SysChassisFanEntry
	MAX-ACCESS not-accessible
	STATUS current
	DESCRIPTION
		"Columns in the sysChassisFan Table"
	INDEX {
		sysChassisFanIndex
	}
	::= { sysChassisFanTable 1 } 

SysChassisFanEntry ::= 
	SEQUENCE {
        	sysChassisFanIndex                                     INTEGER,
        	sysChassisFanStatus                                    INTEGER,
        	sysChassisFanSpeed                                     Integer32
	}

sysChassisFanIndex OBJECT-TYPE 
	SYNTAX INTEGER(1..2147483647)
	MAX-ACCESS read-only
	STATUS current
	DESCRIPTION
		"The index of a chassis fan on the system. It identifies a 
		particular chassis fan."
	::= { sysChassisFanEntry 1 } 

sysChassisFanStatus OBJECT-TYPE 
	SYNTAX INTEGER {
		bad(0),
		good(1),
		notpresent(2)
	}
	MAX-ACCESS read-only
	STATUS current
	DESCRIPTION
		"The status of the indexed chassis fan on the system.,
		This is only supported for the platform where 
		the sensor data is available."
	::= { sysChassisFanEntry 2 } 

sysChassisFanSpeed OBJECT-TYPE 
	SYNTAX Integer32
	MAX-ACCESS read-only
	STATUS current
	DESCRIPTION
		"The actual speed of the indexed chassis fan on the system.
		This is only supported for the platform where the actual 
		fan speed data is available.
		'0' means fan speed is unavailable while the associated chassis status is good."
	::= { sysChassisFanEntry 3 } 

--==================================================================
-- Chassis_power_supply_status_stat
--==================================================================
sysChassisPowerSupplyNumber OBJECT-TYPE 
	SYNTAX INTEGER
	MAX-ACCESS read-only
	STATUS current
	DESCRIPTION
		"The number of sysChassisPowerSupply entries in the table."
	::= { sysChassisPowerSupply 1 } 

sysChassisPowerSupplyTable OBJECT-TYPE
	SYNTAX SEQUENCE OF SysChassisPowerSupplyEntry
	MAX-ACCESS not-accessible
	STATUS current
	DESCRIPTION
		"A table containing information of chassis power supply status of the system."
	::= { sysChassisPowerSupply 2 } 

sysChassisPowerSupplyEntry OBJECT-TYPE
	SYNTAX  SysChassisPowerSupplyEntry
	MAX-ACCESS not-accessible
	STATUS current
	DESCRIPTION
		"Columns in the sysChassisPowerSupply Table"
	INDEX {
		sysChassisPowerSupplyIndex
	}
	::= { sysChassisPowerSupplyTable 1 } 

SysChassisPowerSupplyEntry ::= 
	SEQUENCE {
        	sysChassisPowerSupplyIndex                             INTEGER,
        	sysChassisPowerSupplyStatus                            INTEGER
	}

sysChassisPowerSupplyIndex OBJECT-TYPE 
	SYNTAX INTEGER(1..2147483647)
	MAX-ACCESS read-only
	STATUS current
	DESCRIPTION
		"The index of a power supply  on the system."
	::= { sysChassisPowerSupplyEntry 1 } 

sysChassisPowerSupplyStatus OBJECT-TYPE 
	SYNTAX INTEGER {
		bad(0),
		good(1),
		notpresent(2)
	}
	MAX-ACCESS read-only
	STATUS current
	DESCRIPTION
		"The status of the indexed power supply on the system.,
		This is only supported for the platform where 
		the sensor data is available."
	::= { sysChassisPowerSupplyEntry 2 } 

--==================================================================
-- Chassis_temperature_status_stat
--==================================================================
sysChassisTempNumber OBJECT-TYPE 
	SYNTAX INTEGER
	MAX-ACCESS read-only
	STATUS current
	DESCRIPTION
		"The number of sysChassisTemp entries in the table."
	::= { sysChassisTemp 1 } 

sysChassisTempTable OBJECT-TYPE
	SYNTAX SEQUENCE OF SysChassisTempEntry
	MAX-ACCESS not-accessible
	STATUS current
	DESCRIPTION
		"A table containing information of chassis temperature of the system."
	::= { sysChassisTemp 2 } 

sysChassisTempEntry OBJECT-TYPE
	SYNTAX  SysChassisTempEntry
	MAX-ACCESS not-accessible
	STATUS current
	DESCRIPTION
		"Columns in the sysChassisTemp Table"
	INDEX {
		sysChassisTempIndex
	}
	::= { sysChassisTempTable 1 } 

SysChassisTempEntry ::= 
	SEQUENCE {
        	sysChassisTempIndex                                    INTEGER,
        	sysChassisTempTemperature                              Integer32
	}

sysChassisTempIndex OBJECT-TYPE 
	SYNTAX INTEGER(1..2147483647)
	MAX-ACCESS read-only
	STATUS current
	DESCRIPTION
		"The index of a chassis temperature sensor on the system. 
		It identifies a particular chassis temperature sensor, fan, etc."
	::= { sysChassisTempEntry 1 } 

sysChassisTempTemperature OBJECT-TYPE 
	SYNTAX Integer32
	MAX-ACCESS read-only
	STATUS current
	DESCRIPTION
		"The chassis temperature (in Celsius) of the indexed sensor on the system.,
		This is only supported for the platform where 
		the sensor data is available."
	::= { sysChassisTempEntry 2 } 

--==================================================================
-- Product
--==================================================================
sysProductName OBJECT-TYPE 
	SYNTAX LongDisplayString
	MAX-ACCESS read-only
	STATUS current
	DESCRIPTION
		"The product name."
	::= { sysProduct 1 } 

sysProductVersion OBJECT-TYPE 
	SYNTAX LongDisplayString
	MAX-ACCESS read-only
	STATUS current
	DESCRIPTION
		"The product version."
	::= { sysProduct 2 } 

sysProductBuild OBJECT-TYPE 
	SYNTAX LongDisplayString
	MAX-ACCESS read-only
	STATUS current
	DESCRIPTION
		"The product build number."
	::= { sysProduct 3 } 

sysProductEdition OBJECT-TYPE 
	SYNTAX LongDisplayString
	MAX-ACCESS read-only
	STATUS current
	DESCRIPTION
		"The product edition."
	::= { sysProduct 4 } 

sysProductDate OBJECT-TYPE 
	SYNTAX LongDisplayString
	MAX-ACCESS read-only
	STATUS current
	DESCRIPTION
		"The product build date."
	::= { sysProduct 5 } 

sysProductHotfix OBJECT-TYPE 
	SYNTAX LongDisplayString
	MAX-ACCESS read-only
	STATUS	 deprecated
	DESCRIPTION
		"Deprecated! The 'Edition' field contains the hotfix number, if applicable"
	::= { sysProduct 6 } 

--==================================================================
-- Memory_usage_stat
--==================================================================
sysSubMemoryResetStats OBJECT-TYPE 
	SYNTAX INTEGER
	MAX-ACCESS read-write
	STATUS	 deprecated
	DESCRIPTION
		"Deprecated!.
		The action to reset resetable statistics data in  sysSubMemory. 
		 Setting this value to 1 will reset statistics data. 
		 Note, some statistics data may not be reset including data that are incremental counters."
	::= { sysSubMemory 1 } 

sysSubMemoryNumber OBJECT-TYPE 
	SYNTAX INTEGER
	MAX-ACCESS read-only
	STATUS	 deprecated
	DESCRIPTION
		"Deprecated!.
		The number of sysSubMemory entries in the table."
	::= { sysSubMemory 2 } 

sysSubMemoryTable OBJECT-TYPE
	SYNTAX SEQUENCE OF SysSubMemoryEntry
	MAX-ACCESS not-accessible
	STATUS deprecated
	DESCRIPTION
		"Deprecated! 
		A table containing information of the memory usage for each subsystem."
	::= { sysSubMemory 3 } 

sysSubMemoryEntry OBJECT-TYPE
	SYNTAX  SysSubMemoryEntry
	MAX-ACCESS not-accessible
	STATUS deprecated
	DESCRIPTION
		"Columns in the sysSubMemory Table"
	INDEX {
		sysSubMemoryName
	}
	::= { sysSubMemoryTable 1 } 

SysSubMemoryEntry ::= 
	SEQUENCE {
        	sysSubMemoryName                                       LongDisplayString,
        	sysSubMemoryAllocated                                  Counter64,
        	sysSubMemoryMaxAllocated                               Counter64,
        	sysSubMemorySize                                       Counter64
	}

sysSubMemoryName OBJECT-TYPE 
	SYNTAX LongDisplayString
	MAX-ACCESS read-only
	STATUS	 deprecated
	DESCRIPTION
		"Deprecated! 
		The name of the subsystem."
	::= { sysSubMemoryEntry 1 } 

sysSubMemoryAllocated OBJECT-TYPE 
	SYNTAX Counter64
	MAX-ACCESS read-only
	STATUS	 deprecated
	DESCRIPTION
		"Deprecated!
		The number of bytes currently allocated for this subsystem."
	::= { sysSubMemoryEntry 2 } 

sysSubMemoryMaxAllocated OBJECT-TYPE 
	SYNTAX Counter64
	MAX-ACCESS read-only
	STATUS	 deprecated
	DESCRIPTION
		"Deprecated!
		The maximum number of bytes allocated for this subsystem."
	::= { sysSubMemoryEntry 3 } 

sysSubMemorySize OBJECT-TYPE 
	SYNTAX Counter64
	MAX-ACCESS read-only
	STATUS	 deprecated
	DESCRIPTION
		"Deprecated!
		The size in bytes of each object."
	::= { sysSubMemoryEntry 4 } 

--==================================================================
-- System
--==================================================================
sysSystemName OBJECT-TYPE 
	SYNTAX LongDisplayString
	MAX-ACCESS read-only
	STATUS current
	DESCRIPTION
		"The operating system name."
	::= { sysSystem 1 } 

sysSystemNodeName OBJECT-TYPE 
	SYNTAX LongDisplayString
	MAX-ACCESS read-only
	STATUS current
	DESCRIPTION
		"The host name of the system on the network."
	::= { sysSystem 2 } 

sysSystemRelease OBJECT-TYPE 
	SYNTAX LongDisplayString
	MAX-ACCESS read-only
	STATUS current
	DESCRIPTION
		"The current system release level."
	::= { sysSystem 3 } 

sysSystemVersion OBJECT-TYPE 
	SYNTAX LongDisplayString
	MAX-ACCESS read-only
	STATUS current
	DESCRIPTION
		"The current system version level."
	::= { sysSystem 4 } 

sysSystemMachine OBJECT-TYPE 
	SYNTAX LongDisplayString
	MAX-ACCESS read-only
	STATUS current
	DESCRIPTION
		"The name of the hardware type the system is running."
	::= { sysSystem 5 } 

sysSystemUptime OBJECT-TYPE 
	SYNTAX TimeTicks
	MAX-ACCESS read-only
	STATUS current
	DESCRIPTION
		"The system up time in 1/100 seconds since boot."
	::= { sysSystem 6 } 

sysSystemUptimeInSec OBJECT-TYPE 
	SYNTAX Integer32
	MAX-ACCESS read-only
	STATUS current
	DESCRIPTION
		"The system up time in seconds since boot."
	::= { sysSystem 7 } 

--==================================================================
-- Global_fasthttp_stat
--==================================================================
sysFastHttpStatResetStats OBJECT-TYPE 
	SYNTAX INTEGER
	MAX-ACCESS read-write
	STATUS current
	DESCRIPTION
		"The action to reset resetable statistics data in  sysGlobalFastHttpStat. 
		 Setting this value to 1 will reset statistics data. 
		 Note, some statistics data may not be reset including data that are incremental counters."
	::= { sysGlobalFastHttpStat 1 } 

sysFastHttpStatClientSyns OBJECT-TYPE 
	SYNTAX Counter64
	MAX-ACCESS read-only
	STATUS current
	DESCRIPTION
		"The total number of client SYN cookies generated."
	::= { sysGlobalFastHttpStat 2 } 

sysFastHttpStatClientAccepts OBJECT-TYPE 
	SYNTAX Counter64
	MAX-ACCESS read-only
	STATUS current
	DESCRIPTION
		"The total number of client TCP accepts."
	::= { sysGlobalFastHttpStat 3 } 

sysFastHttpStatServerConnects OBJECT-TYPE 
	SYNTAX Counter64
	MAX-ACCESS read-only
	STATUS current
	DESCRIPTION
		"The total number of server TCP connects."
	::= { sysGlobalFastHttpStat 4 } 

sysFastHttpStatConnpoolCurSize OBJECT-TYPE 
	SYNTAX Integer32
	MAX-ACCESS read-only
	STATUS current
	DESCRIPTION
		"The number of available server-side flows in the reuse pools."
	::= { sysGlobalFastHttpStat 5 } 

sysFastHttpStatConnpoolMaxSize OBJECT-TYPE 
	SYNTAX Integer32
	MAX-ACCESS read-only
	STATUS current
	DESCRIPTION
		"The maximum number of available server-side flows in the reuse pools."
	::= { sysGlobalFastHttpStat 6 } 

sysFastHttpStatConnpoolReuses OBJECT-TYPE 
	SYNTAX Counter64
	MAX-ACCESS read-only
	STATUS current
	DESCRIPTION
		"The number of times a server-side flow was reused from the pools."
	::= { sysGlobalFastHttpStat 7 } 

sysFastHttpStatConnpoolExhausted OBJECT-TYPE 
	SYNTAX Counter64
	MAX-ACCESS read-only
	STATUS current
	DESCRIPTION
		"The number of times the reuse pools was exhausted."
	::= { sysGlobalFastHttpStat 8 } 

sysFastHttpStatNumberReqs OBJECT-TYPE 
	SYNTAX Counter64
	MAX-ACCESS read-only
	STATUS current
	DESCRIPTION
		"The total number of http requests."
	::= { sysGlobalFastHttpStat 9 } 

sysFastHttpStatUnbufferedReqs OBJECT-TYPE 
	SYNTAX Counter64
	MAX-ACCESS read-only
	STATUS current
	DESCRIPTION
		"The total number of un-buffered requests."
	::= { sysGlobalFastHttpStat 10 } 

sysFastHttpStatGetReqs OBJECT-TYPE 
	SYNTAX Counter64
	MAX-ACCESS read-only
	STATUS current
	DESCRIPTION
		"The total number of get requests."
	::= { sysGlobalFastHttpStat 11 } 

sysFastHttpStatPostReqs OBJECT-TYPE 
	SYNTAX Counter64
	MAX-ACCESS read-only
	STATUS current
	DESCRIPTION
		"The total number of post requests."
	::= { sysGlobalFastHttpStat 12 } 

sysFastHttpStatV9Reqs OBJECT-TYPE 
	SYNTAX Counter64
	MAX-ACCESS read-only
	STATUS current
	DESCRIPTION
		"The total number of version 9 requests."
	::= { sysGlobalFastHttpStat 13 } 

sysFastHttpStatV10Reqs OBJECT-TYPE 
	SYNTAX Counter64
	MAX-ACCESS read-only
	STATUS current
	DESCRIPTION
		"The total number of version 10 requests."
	::= { sysGlobalFastHttpStat 14 } 

sysFastHttpStatV11Reqs OBJECT-TYPE 
	SYNTAX Counter64
	MAX-ACCESS read-only
	STATUS current
	DESCRIPTION
		"The total number of version 11 requests."
	::= { sysGlobalFastHttpStat 15 } 

sysFastHttpStatResp2xxCnt OBJECT-TYPE 
	SYNTAX Counter64
	MAX-ACCESS read-only
	STATUS current
	DESCRIPTION
		"The number of server-side responses in range of 200 to 206 
		(successful responses)."
	::= { sysGlobalFastHttpStat 16 } 

sysFastHttpStatResp3xxCnt OBJECT-TYPE 
	SYNTAX Counter64
	MAX-ACCESS read-only
	STATUS current
	DESCRIPTION
		"The number of server-side responses in range of 300 to 307 
		(redirection responses)."
	::= { sysGlobalFastHttpStat 17 } 

sysFastHttpStatResp4xxCnt OBJECT-TYPE 
	SYNTAX Counter64
	MAX-ACCESS read-only
	STATUS current
	DESCRIPTION
		"The number of server-side responses in range of 400 to 417 (client errors). "
	::= { sysGlobalFastHttpStat 18 } 

sysFastHttpStatResp5xxCnt OBJECT-TYPE 
	SYNTAX Counter64
	MAX-ACCESS read-only
	STATUS current
	DESCRIPTION
		"The number of server-side responses in range of 500 to 505 (server errors)."
	::= { sysGlobalFastHttpStat 19 } 

sysFastHttpStatReqParseErrors OBJECT-TYPE 
	SYNTAX Counter64
	MAX-ACCESS read-only
	STATUS current
	DESCRIPTION
		"The number of request parse errors."
	::= { sysGlobalFastHttpStat 20 } 

sysFastHttpStatRespParseErrors OBJECT-TYPE 
	SYNTAX Counter64
	MAX-ACCESS read-only
	STATUS current
	DESCRIPTION
		"The number of response parse errors."
	::= { sysGlobalFastHttpStat 21 } 

sysFastHttpStatClientRxBad OBJECT-TYPE 
	SYNTAX Counter64
	MAX-ACCESS read-only
	STATUS current
	DESCRIPTION
		"The number of bad TCP segments dropped from client-side."
	::= { sysGlobalFastHttpStat 22 } 

sysFastHttpStatServerRxBad OBJECT-TYPE 
	SYNTAX Counter64
	MAX-ACCESS read-only
	STATUS current
	DESCRIPTION
		"The number of bad TCP segments dropped from server-side."
	::= { sysGlobalFastHttpStat 23 } 

sysFastHttpStatPipelinedReqs OBJECT-TYPE 
	SYNTAX Counter64
	MAX-ACCESS read-only
	STATUS current
	DESCRIPTION
		"The number of pipelined HTTP requests detected."
	::= { sysGlobalFastHttpStat 24 } 

--==================================================================
-- Global_xml_stat
--==================================================================
sysXmlStatResetStats OBJECT-TYPE 
	SYNTAX INTEGER
	MAX-ACCESS read-write
	STATUS current
	DESCRIPTION
		"The action to reset resetable statistics data in  sysGlobalXmlStat. 
		 Setting this value to 1 will reset statistics data. 
		 Note, some statistics data may not be reset including data that are incremental counters."
	::= { sysGlobalXmlStat 1 } 

sysXmlStatNumErrors OBJECT-TYPE 
	SYNTAX Counter64
	MAX-ACCESS read-only
	STATUS	 deprecated
	DESCRIPTION
		"Deprecated! The total number of XML parsing errors."
	::= { sysGlobalXmlStat 2 } 

--==================================================================
-- System_information
--==================================================================
sysGeneralHwName OBJECT-TYPE 
	SYNTAX LongDisplayString
	MAX-ACCESS read-only
	STATUS current
	DESCRIPTION
		"The name of the system hardware model."
	::= { sysGeneral 1 } 

sysGeneralHwNumber OBJECT-TYPE 
	SYNTAX LongDisplayString
	MAX-ACCESS read-only
	STATUS	 deprecated
	DESCRIPTION
		"Deprecated! 
		   The name of the system model. This is replaced by platform.marketing_name"
	::= { sysGeneral 2 } 

sysGeneralChassisSerialNum OBJECT-TYPE 
	SYNTAX LongDisplayString
	MAX-ACCESS read-only
	STATUS current
	DESCRIPTION
		"The system serial number."
	::= { sysGeneral 3 } 

--==================================================================
-- Global_iiop_stat
--==================================================================
sysIiopStatResetStats OBJECT-TYPE 
	SYNTAX INTEGER
	MAX-ACCESS read-write
	STATUS current
	DESCRIPTION
		"The action to reset resetable statistics data in  sysGlobalIiopStat. 
		 Setting this value to 1 will reset statistics data. 
		 Note, some statistics data may not be reset including data that are incremental counters."
	::= { sysGlobalIiopStat 1 } 

sysIiopStatNumRequests OBJECT-TYPE 
	SYNTAX Counter64
	MAX-ACCESS read-only
	STATUS current
	DESCRIPTION
		"The total number of IIOP requests."
	::= { sysGlobalIiopStat 2 } 

sysIiopStatNumResponses OBJECT-TYPE 
	SYNTAX Counter64
	MAX-ACCESS read-only
	STATUS current
	DESCRIPTION
		"The total number of IIOP responses."
	::= { sysGlobalIiopStat 3 } 

sysIiopStatNumCancels OBJECT-TYPE 
	SYNTAX Counter64
	MAX-ACCESS read-only
	STATUS current
	DESCRIPTION
		"The total number of IIOP cancel messages."
	::= { sysGlobalIiopStat 4 } 

sysIiopStatNumErrors OBJECT-TYPE 
	SYNTAX Counter64
	MAX-ACCESS read-only
	STATUS current
	DESCRIPTION
		"The total number of IIOP error messages."
	::= { sysGlobalIiopStat 5 } 

sysIiopStatNumFragments OBJECT-TYPE 
	SYNTAX Counter64
	MAX-ACCESS read-only
	STATUS current
	DESCRIPTION
		"The total number of IIOP fragments."
	::= { sysGlobalIiopStat 6 } 

--==================================================================
-- Global_rtsp_stat
--==================================================================
sysRtspStatResetStats OBJECT-TYPE 
	SYNTAX INTEGER
	MAX-ACCESS read-write
	STATUS current
	DESCRIPTION
		"The action to reset resetable statistics data in  sysGlobalRtspStat. 
		 Setting this value to 1 will reset statistics data. 
		 Note, some statistics data may not be reset including data that are incremental counters."
	::= { sysGlobalRtspStat 1 } 

sysRtspStatNumRequests OBJECT-TYPE 
	SYNTAX Counter64
	MAX-ACCESS read-only
	STATUS current
	DESCRIPTION
		"The total number of RTSP requests."
	::= { sysGlobalRtspStat 2 } 

sysRtspStatNumResponses OBJECT-TYPE 
	SYNTAX Counter64
	MAX-ACCESS read-only
	STATUS current
	DESCRIPTION
		"The total number of RTSP responses."
	::= { sysGlobalRtspStat 3 } 

sysRtspStatNumErrors OBJECT-TYPE 
	SYNTAX Counter64
	MAX-ACCESS read-only
	STATUS current
	DESCRIPTION
		"The total number of RTSP errors."
	::= { sysGlobalRtspStat 4 } 

sysRtspStatNumInterleavedData OBJECT-TYPE 
	SYNTAX Counter64
	MAX-ACCESS read-only
	STATUS current
	DESCRIPTION
		"The total number of interleaved RTSP data packets."
	::= { sysGlobalRtspStat 5 } 

--==================================================================
-- Global_sctp_stat
--==================================================================
sysSctpStatResetStats OBJECT-TYPE 
	SYNTAX INTEGER
	MAX-ACCESS read-write
	STATUS current
	DESCRIPTION
		"The action to reset resetable statistics data in  sysGlobalSctpStat. 
		 Setting this value to 1 will reset statistics data. 
		 Note, some statistics data may not be reset including data that are incremental counters."
	::= { sysGlobalSctpStat 1 } 

sysSctpStatAccepts OBJECT-TYPE 
	SYNTAX Counter64
	MAX-ACCESS read-only
	STATUS current
	DESCRIPTION
		"The total number of accepted connections."
	::= { sysGlobalSctpStat 2 } 

sysSctpStatAcceptfails OBJECT-TYPE 
	SYNTAX Counter64
	MAX-ACCESS read-only
	STATUS current
	DESCRIPTION
		"The total number of not accepted responses."
	::= { sysGlobalSctpStat 3 } 

sysSctpStatConnects OBJECT-TYPE 
	SYNTAX Counter64
	MAX-ACCESS read-only
	STATUS current
	DESCRIPTION
		"The total number of established connections."
	::= { sysGlobalSctpStat 4 } 

sysSctpStatConnfails OBJECT-TYPE 
	SYNTAX Counter64
	MAX-ACCESS read-only
	STATUS current
	DESCRIPTION
		"The total number of connections failures."
	::= { sysGlobalSctpStat 5 } 

sysSctpStatExpires OBJECT-TYPE 
	SYNTAX Counter64
	MAX-ACCESS read-only
	STATUS current
	DESCRIPTION
		"The total number of expired connections due to idle timeout."
	::= { sysGlobalSctpStat 6 } 

sysSctpStatAbandons OBJECT-TYPE 
	SYNTAX Counter64
	MAX-ACCESS read-only
	STATUS current
	DESCRIPTION
		"The total number of abandoned connections due to retries/keep-alives."
	::= { sysGlobalSctpStat 7 } 

sysSctpStatRxrst OBJECT-TYPE 
	SYNTAX Counter64
	MAX-ACCESS read-only
	STATUS current
	DESCRIPTION
		"The total number of received Abort chunks."
	::= { sysGlobalSctpStat 8 } 

sysSctpStatRxbadsum OBJECT-TYPE 
	SYNTAX Counter64
	MAX-ACCESS read-only
	STATUS current
	DESCRIPTION
		"The total number of bad checksum in received packets."
	::= { sysGlobalSctpStat 9 } 

sysSctpStatRxcookie OBJECT-TYPE 
	SYNTAX Counter64
	MAX-ACCESS read-only
	STATUS current
	DESCRIPTION
		"The total number of received SCTP cookies (including bad and good ones)."
	::= { sysGlobalSctpStat 10 } 

sysSctpStatRxbadcookie OBJECT-TYPE 
	SYNTAX Counter64
	MAX-ACCESS read-only
	STATUS current
	DESCRIPTION
		"The total number of received bad SCTP cookies."
	::= { sysGlobalSctpStat 11 } 

--==================================================================
-- L2_forward_stat
--==================================================================
sysL2ForwardStatNumber OBJECT-TYPE 
	SYNTAX INTEGER
	MAX-ACCESS read-only
	STATUS current
	DESCRIPTION
		"The number of sysL2ForwardStat entries in the table."
	::= { sysL2ForwardStat 1 } 

sysL2ForwardStatTable OBJECT-TYPE
	SYNTAX SEQUENCE OF SysL2ForwardStatEntry
	MAX-ACCESS not-accessible
	STATUS current
	DESCRIPTION
		"A table containing current entries (dynamic and static) of 
		L2 forwarding information. An object of this type is transient.
		By default, this table displays nothing until sysL2ForwardAttrVlan
		is set."
	::= { sysL2ForwardStat 2 } 

sysL2ForwardStatEntry OBJECT-TYPE
	SYNTAX  SysL2ForwardStatEntry
	MAX-ACCESS not-accessible
	STATUS current
	DESCRIPTION
		"Columns in the sysL2ForwardStat Table"
	INDEX {
		sysL2ForwardStatVlanName,
		sysL2ForwardStatMacAddr
	}
	::= { sysL2ForwardStatTable 1 } 

SysL2ForwardStatEntry ::= 
	SEQUENCE {
        	sysL2ForwardStatVlanName                               LongDisplayString,
        	sysL2ForwardStatMacAddr                                MacAddress,
        	sysL2ForwardStatIfname                                 LongDisplayString,
        	sysL2ForwardStatIftype                                 INTEGER,
        	sysL2ForwardStatDynamic                                INTEGER
	}

sysL2ForwardStatVlanName OBJECT-TYPE 
	SYNTAX LongDisplayString
	MAX-ACCESS read-only
	STATUS current
	DESCRIPTION
		"The VLAN name which static forward entity is from."
	::= { sysL2ForwardStatEntry 1 } 

sysL2ForwardStatMacAddr OBJECT-TYPE 
	SYNTAX MacAddress
	MAX-ACCESS read-only
	STATUS current
	DESCRIPTION
		"The MAC address for the specified VLAN."
	::= { sysL2ForwardStatEntry 2 } 

sysL2ForwardStatIfname OBJECT-TYPE 
	SYNTAX LongDisplayString
	MAX-ACCESS read-only
	STATUS current
	DESCRIPTION
		"The name of interface for the specified VLAN."
	::= { sysL2ForwardStatEntry 3 } 

sysL2ForwardStatIftype OBJECT-TYPE 
	SYNTAX INTEGER {
		interface(0),
		trunk(1)
	}
	MAX-ACCESS read-only
	STATUS current
	DESCRIPTION
		"The type of interface for the specified VLAN."
	::= { sysL2ForwardStatEntry 4 } 

sysL2ForwardStatDynamic OBJECT-TYPE 
	SYNTAX INTEGER {
		false(0),
		true(1)
	}
	MAX-ACCESS read-only
	STATUS current
	DESCRIPTION
		"The dynamic state of the specified entity."
	::= { sysL2ForwardStatEntry 5 } 

--==================================================================
-- L2_forward_attr
--==================================================================
sysL2ForwardAttrVlan OBJECT-TYPE 
	SYNTAX LongDisplayString
	MAX-ACCESS read-write
	STATUS current
	DESCRIPTION
		"The VLAN name which is used for querying sysL2ForwardStat.
		sysL2ForwardStat will display L2 forward statistics associated 
		VLAN specified here. The default is set to 'none', which means 
		sysL2ForwardStat will display nothing. If this is set to 'all', 
		sysL2ForwardStat will display for all VLANs."
	::= { sysL2ForwardAttr 1 } 

--==================================================================
-- Memory_info_stat
--==================================================================
sysHostMemoryTotal OBJECT-TYPE 
	SYNTAX CounterBasedGauge64
	MAX-ACCESS read-only
	STATUS current
	DESCRIPTION
		"The total host memory in bytes. 
		This is for a single host system. For multiple host system, 
		please refer sysMultiHost table."
	::= { sysHostMemory 1 } 

sysHostMemoryUsed OBJECT-TYPE 
	SYNTAX CounterBasedGauge64
	MAX-ACCESS read-only
	STATUS current
	DESCRIPTION
		"The host memory in bytes currently in use.
		This is for a single host system. For multiple host system, 
		please refer sysMultiHost table."
	::= { sysHostMemory 2 } 

--==================================================================
-- Cpu_info_stat
--==================================================================
sysHostCpuNumber OBJECT-TYPE 
	SYNTAX INTEGER
	MAX-ACCESS read-only
	STATUS	 deprecated
	DESCRIPTION
		"Deprecated!.
		The number of sysHostCpu entries in the table."
	::= { sysHostCpu 1 } 

sysHostCpuTable OBJECT-TYPE
	SYNTAX SEQUENCE OF SysHostCpuEntry
	MAX-ACCESS not-accessible
	STATUS deprecated
	DESCRIPTION
		"Deprecated! Replaced by sysMultiHostCpu table.
		A table containing entries of system CPU usage information. This is for a single host system."
	::= { sysHostCpu 2 } 

sysHostCpuEntry OBJECT-TYPE
	SYNTAX  SysHostCpuEntry
	MAX-ACCESS not-accessible
	STATUS deprecated
	DESCRIPTION
		"Columns in the sysHostCpu Table"
	INDEX {
		sysHostCpuIndex
	}
	::= { sysHostCpuTable 1 } 

SysHostCpuEntry ::= 
	SEQUENCE {
        	sysHostCpuIndex                                        INTEGER,
        	sysHostCpuId                                           Integer32,
        	sysHostCpuUser                                         Counter64,
        	sysHostCpuNice                                         Counter64,
        	sysHostCpuSystem                                       Counter64,
        	sysHostCpuIdle                                         Counter64,
        	sysHostCpuIrq                                          Counter64,
        	sysHostCpuSoftirq                                      Counter64,
        	sysHostCpuIowait                                       Counter64
	}

sysHostCpuIndex OBJECT-TYPE 
	SYNTAX INTEGER(1..2147483647)
	MAX-ACCESS read-only
	STATUS	 deprecated
	DESCRIPTION
		"Deprecated! Replaced by sysMultiHostCpu table.
		 The index of a CPU in this CPU table."
	::= { sysHostCpuEntry 1 } 

sysHostCpuId OBJECT-TYPE 
	SYNTAX Integer32
	MAX-ACCESS read-only
	STATUS	 deprecated
	DESCRIPTION
		"Deprecated! Replaced by sysMultiHostCpu table.
		The ID of a processor."
	::= { sysHostCpuEntry 2 } 

sysHostCpuUser OBJECT-TYPE 
	SYNTAX Counter64
	MAX-ACCESS read-only
	STATUS	 deprecated
	DESCRIPTION
		"Deprecated! Replaced by sysMultiHostCpu table.
		The time spent by the specified processor in user context."
	::= { sysHostCpuEntry 3 } 

sysHostCpuNice OBJECT-TYPE 
	SYNTAX Counter64
	MAX-ACCESS read-only
	STATUS	 deprecated
	DESCRIPTION
		"Deprecated! Replaced by sysMultiHostCpu table.
		The time spent by the specified processor running niced processes."
	::= { sysHostCpuEntry 4 } 

sysHostCpuSystem OBJECT-TYPE 
	SYNTAX Counter64
	MAX-ACCESS read-only
	STATUS	 deprecated
	DESCRIPTION
		"Deprecated! Replaced by sysMultiHostCpu table.
		The time spent by the specified processor servicing system calls."
	::= { sysHostCpuEntry 5 } 

sysHostCpuIdle OBJECT-TYPE 
	SYNTAX Counter64
	MAX-ACCESS read-only
	STATUS	 deprecated
	DESCRIPTION
		"Deprecated! Replaced by sysMultiHostCpu table.
		The time spent by the specified processor doing nothing."
	::= { sysHostCpuEntry 6 } 

sysHostCpuIrq OBJECT-TYPE 
	SYNTAX Counter64
	MAX-ACCESS read-only
	STATUS	 deprecated
	DESCRIPTION
		"Deprecated! Replaced by sysMultiHostCpu table.
		The time spent by the specified processor servicing hardware interrupts."
	::= { sysHostCpuEntry 7 } 

sysHostCpuSoftirq OBJECT-TYPE 
	SYNTAX Counter64
	MAX-ACCESS read-only
	STATUS	 deprecated
	DESCRIPTION
		"Deprecated! Replaced by sysMultiHostCpu table.
		The time spent by the specified processor servicing soft interrupts."
	::= { sysHostCpuEntry 8 } 

sysHostCpuIowait OBJECT-TYPE 
	SYNTAX Counter64
	MAX-ACCESS read-only
	STATUS	 deprecated
	DESCRIPTION
		"Deprecated! Replaced by sysMultiHostCpu table.
		The time spent by the specified processor waiting for external I/O to complete."
	::= { sysHostCpuEntry 9 } 

--==================================================================
-- Disk_info_stat
--==================================================================
sysHostDiskNumber OBJECT-TYPE 
	SYNTAX INTEGER
	MAX-ACCESS read-only
	STATUS current
	DESCRIPTION
		"The number of sysHostDisk entries in the table."
	::= { sysHostDisk 1 } 

sysHostDiskTable OBJECT-TYPE
	SYNTAX SEQUENCE OF SysHostDiskEntry
	MAX-ACCESS not-accessible
	STATUS current
	DESCRIPTION
		"A table containing entries of system disk usage information."
	::= { sysHostDisk 2 } 

sysHostDiskEntry OBJECT-TYPE
	SYNTAX  SysHostDiskEntry
	MAX-ACCESS not-accessible
	STATUS current
	DESCRIPTION
		"Columns in the sysHostDisk Table"
	INDEX {
		sysHostDiskPartition
	}
	::= { sysHostDiskTable 1 } 

SysHostDiskEntry ::= 
	SEQUENCE {
        	sysHostDiskPartition                                   LongDisplayString,
        	sysHostDiskBlockSize                                   Integer32,
        	sysHostDiskTotalBlocks                                 Integer32,
        	sysHostDiskFreeBlocks                                  Integer32,
        	sysHostDiskTotalNodes                                  Integer32,
        	sysHostDiskFreeNodes                                   Integer32
	}

sysHostDiskPartition OBJECT-TYPE 
	SYNTAX LongDisplayString
	MAX-ACCESS read-only
	STATUS current
	DESCRIPTION
		"The name of a disk partition."
	::= { sysHostDiskEntry 1 } 

sysHostDiskBlockSize OBJECT-TYPE 
	SYNTAX Integer32
	MAX-ACCESS read-only
	STATUS current
	DESCRIPTION
		"The number of bytes in the specified partition."
	::= { sysHostDiskEntry 2 } 

sysHostDiskTotalBlocks OBJECT-TYPE 
	SYNTAX Integer32
	MAX-ACCESS read-only
	STATUS current
	DESCRIPTION
		"The number of total blocks in the specified partition."
	::= { sysHostDiskEntry 3 } 

sysHostDiskFreeBlocks OBJECT-TYPE 
	SYNTAX Integer32
	MAX-ACCESS read-only
	STATUS current
	DESCRIPTION
		"The number of free blocks in the specified partition."
	::= { sysHostDiskEntry 4 } 

sysHostDiskTotalNodes OBJECT-TYPE 
	SYNTAX Integer32
	MAX-ACCESS read-only
	STATUS current
	DESCRIPTION
		"The number of total file nodes in the specified partition."
	::= { sysHostDiskEntry 5 } 

sysHostDiskFreeNodes OBJECT-TYPE 
	SYNTAX Integer32
	MAX-ACCESS read-only
	STATUS current
	DESCRIPTION
		"The number of free file nodes in the specified partition."
	::= { sysHostDiskEntry 6 } 

--==================================================================
-- Self_port_default
--==================================================================
sysSelfPortDefNumber OBJECT-TYPE 
	SYNTAX INTEGER
	MAX-ACCESS read-only
	STATUS current
	DESCRIPTION
		"The number of sysSelfPortDefault entries in the table."
	::= { sysSelfPortDefault 1 } 

sysSelfPortDefTable OBJECT-TYPE
	SYNTAX SEQUENCE OF SysSelfPortDefEntry
	MAX-ACCESS not-accessible
	STATUS current
	DESCRIPTION
		"A table containing information of default protocol/service access list."
	::= { sysSelfPortDefault 2 } 

sysSelfPortDefEntry OBJECT-TYPE
	SYNTAX  SysSelfPortDefEntry
	MAX-ACCESS not-accessible
	STATUS current
	DESCRIPTION
		"Columns in the sysSelfPortDef Table"
	INDEX {
		sysSelfPortDefAllowName,
		sysSelfPortDefProtocol,
		sysSelfPortDefPort
	}
	::= { sysSelfPortDefTable 1 } 

SysSelfPortDefEntry ::= 
	SEQUENCE {
        	sysSelfPortDefProtocol                                 INTEGER,
        	sysSelfPortDefPort                                     InetPortNumber,
        	sysSelfPortDefAllowName                                LongDisplayString
	}

sysSelfPortDefProtocol OBJECT-TYPE 
	SYNTAX INTEGER(0..256)
	MAX-ACCESS read-only
	STATUS current
	DESCRIPTION
		"The default protocol allowed.
		'0' means allowing all protocols."
	::= { sysSelfPortDefEntry 1 } 

sysSelfPortDefPort OBJECT-TYPE 
	SYNTAX InetPortNumber
	MAX-ACCESS read-only
	STATUS current
	DESCRIPTION
		"The default service allowed.
		'0' means allowing all services for the specified protocol(s)."
	::= { sysSelfPortDefEntry 2 } 

sysSelfPortDefAllowName OBJECT-TYPE 
	SYNTAX LongDisplayString
	MAX-ACCESS read-only
	STATUS current
	DESCRIPTION
		"The allow name of self port default."
	::= { sysSelfPortDefEntry 3 } 

--==================================================================
-- Interface_media_options_sfp
--==================================================================
sysIntfMediaSfpNumber OBJECT-TYPE 
	SYNTAX INTEGER
	MAX-ACCESS read-only
	STATUS current
	DESCRIPTION
		"The number of sysInterfaceMediaSfp entries in the table."
	::= { sysInterfaceMediaSfp 1 } 

sysIntfMediaSfpTable OBJECT-TYPE
	SYNTAX SEQUENCE OF SysIntfMediaSfpEntry
	MAX-ACCESS not-accessible
	STATUS current
	DESCRIPTION
		"A table containing information of the SFP media options of the interfaces."
	::= { sysInterfaceMediaSfp 2 } 

sysIntfMediaSfpEntry OBJECT-TYPE
	SYNTAX  SysIntfMediaSfpEntry
	MAX-ACCESS not-accessible
	STATUS current
	DESCRIPTION
		"Columns in the sysIntfMediaSfp Table"
	INDEX {
		sysIntfMediaSfpName,
		sysIntfMediaSfpIndex
	}
	::= { sysIntfMediaSfpTable 1 } 

SysIntfMediaSfpEntry ::= 
	SEQUENCE {
        	sysIntfMediaSfpName                                    LongDisplayString,
        	sysIntfMediaSfpIndex                                   INTEGER,
        	sysIntfMediaSfpType                                    INTEGER
	}

sysIntfMediaSfpName OBJECT-TYPE 
	SYNTAX LongDisplayString
	MAX-ACCESS read-only
	STATUS current
	DESCRIPTION
		"The name of an interface."
	::= { sysIntfMediaSfpEntry 1 } 

sysIntfMediaSfpIndex OBJECT-TYPE 
	SYNTAX INTEGER(1..2147483647)
	MAX-ACCESS read-only
	STATUS current
	DESCRIPTION
		"The index of the SFP media option for the specified interface."
	::= { sysIntfMediaSfpEntry 2 } 

sysIntfMediaSfpType OBJECT-TYPE 
	SYNTAX INTEGER {
		media10THdx(1),
		media10TFdx(2),
		media100TxHdx(3),
		media100TxFdx(4),
		media1000THdx(5),
		media1000TFdx(6),
		media10000TFdx(10),
		mediaAuto(13),
		mediaInternal(14),
		media1000SxFdx(16),
		media1000LxFdx(18),
		media10000SrFdx(19),
		media10000LrFdx(20),
		media10000ErFdx(21),
		media1000CxFdx(22),
		media10000SfpPlusCuFdx(23),
		media40000Sr4Fdx(24),
		media40000Lr4Fdx(25)
	}
	MAX-ACCESS read-only
	STATUS current
	DESCRIPTION
		"The media option for SFP media of the specified interface.
		media10THdx - 10BaseT:RJ45, half duplex,
		media10TFdx - 10BaseT:RJ45, full duplex,
		media100TxHdx - 100BaseTX:RJ45, half duplex,
		media100TxFdx - 100BaseTX:RJ45, full duplex,
		media1000THdx - 1000BaseT - gigabit ethernet RJ45, half duplex,
		media1000TFdx - 1000BaseTX:gigabit ethernet RJ45, full duplex,
		media10000TFdx - 10000BaseT - 10gig Ethernet - Copper, full duplex,
		mediaAuto - autoselect best media,
		mediaInternal - this media option is only used internally,
		media1000SxFdx - 1000BaseSX: gigabit over fiber - Shortwave, full duplex,
		media1000LxFdx - 1000BaseLX - gigabit over fiber - Longwave, half duplex,
		media10000SrFdx - 10GBase-SR - Shortwave 850nm multimode fiber - 300m max - serial 64B/66B encoding, full duplex,
		media10000LrFdx - 10GBase-LR - Longwave 1310nm single mode fiber - 10km max - serial 64B/66B encoding, full duplex,
		media10000ErFdx - 10GBase-ER - Extra longwave 1550nm single mode fiber - 40km max - serial 64B/66B encoding, full duplex,
		media1000CxFdx - 1000BaseCX: Copper, full duplex,
		media10000SfpPlusCuFdx - 10G SFP+: Copper, full duplex,
		media40000Sr4Fdx - 40GBase: fiber, Shortwave (850nm), full duplex,
		media40000Lr4Fdx - 40GBase: fiber, Longwave (1310nm), full duplex."
	::= { sysIntfMediaSfpEntry 3 } 

--==================================================================
-- Pva_stat
--==================================================================
sysPvaStatResetStats OBJECT-TYPE 
	SYNTAX INTEGER
	MAX-ACCESS read-write
	STATUS current
	DESCRIPTION
		"The action to reset resetable statistics data in  sysPvaStat. 
		 Setting this value to 1 will reset statistics data. 
		 Note, some statistics data may not be reset including data that are incremental counters."
	::= { sysPvaStat 1 } 

sysPvaStatNumber OBJECT-TYPE 
	SYNTAX INTEGER
	MAX-ACCESS read-only
	STATUS current
	DESCRIPTION
		"The number of sysPvaStat entries in the table."
	::= { sysPvaStat 2 } 

sysPvaStatTable OBJECT-TYPE
	SYNTAX SEQUENCE OF SysPvaStatEntry
	MAX-ACCESS not-accessible
	STATUS current
	DESCRIPTION
		"A table containing statistics information of the Packet Velocity Acceleration Engine (PVA) on the system."
	::= { sysPvaStat 3 } 

sysPvaStatEntry OBJECT-TYPE
	SYNTAX  SysPvaStatEntry
	MAX-ACCESS not-accessible
	STATUS current
	DESCRIPTION
		"Columns in the sysPvaStat Table"
	INDEX {
		sysPvaStatPvaId
	}
	::= { sysPvaStatTable 1 } 

SysPvaStatEntry ::= 
	SEQUENCE {
        	sysPvaStatPvaId                                        LongDisplayString,
        	sysPvaStatClientPktsIn                                 Counter64,
        	sysPvaStatClientBytesIn                                Counter64,
        	sysPvaStatClientPktsOut                                Counter64,
        	sysPvaStatClientBytesOut                               Counter64,
        	sysPvaStatClientMaxConns                               Counter64,
        	sysPvaStatClientTotConns                               Counter64,
        	sysPvaStatClientCurConns                               CounterBasedGauge64,
        	sysPvaStatServerPktsIn                                 Counter64,
        	sysPvaStatServerBytesIn                                Counter64,
        	sysPvaStatServerPktsOut                                Counter64,
        	sysPvaStatServerBytesOut                               Counter64,
        	sysPvaStatServerMaxConns                               Counter64,
        	sysPvaStatServerTotConns                               Counter64,
        	sysPvaStatServerCurConns                               CounterBasedGauge64,
        	sysPvaStatTotAssistConns                               Counter64,
        	sysPvaStatCurAssistConns                               CounterBasedGauge64,
        	sysPvaStatHardSyncookieGen                             Counter64,
        	sysPvaStatHardSyncookieDet                             Counter64
	}

sysPvaStatPvaId OBJECT-TYPE 
	SYNTAX LongDisplayString
	MAX-ACCESS read-only
	STATUS current
	DESCRIPTION
		"The ID of PVA (Packet Velocity Acceleration Engine) on the system."
	::= { sysPvaStatEntry 1 } 

sysPvaStatClientPktsIn OBJECT-TYPE 
	SYNTAX Counter64
	MAX-ACCESS read-only
	STATUS current
	DESCRIPTION
		"The number of hardware accelerated packets received 
		by the system from client-side."
	::= { sysPvaStatEntry 2 } 

sysPvaStatClientBytesIn OBJECT-TYPE 
	SYNTAX Counter64
	MAX-ACCESS read-only
	STATUS current
	DESCRIPTION
		"The number of hardware accelerated bytes received 
		by the system from client-side."
	::= { sysPvaStatEntry 3 } 

sysPvaStatClientPktsOut OBJECT-TYPE 
	SYNTAX Counter64
	MAX-ACCESS read-only
	STATUS current
	DESCRIPTION
		"The number of hardware accelerated packets sent to client-side from the system."
	::= { sysPvaStatEntry 4 } 

sysPvaStatClientBytesOut OBJECT-TYPE 
	SYNTAX Counter64
	MAX-ACCESS read-only
	STATUS current
	DESCRIPTION
		"The number of hardware accelerated bytes sent to client-side from the system."
	::= { sysPvaStatEntry 5 } 

sysPvaStatClientMaxConns OBJECT-TYPE 
	SYNTAX Counter64
	MAX-ACCESS read-only
	STATUS current
	DESCRIPTION
		"The maximum hardware accelerated connections from client-side to the system."
	::= { sysPvaStatEntry 6 } 

sysPvaStatClientTotConns OBJECT-TYPE 
	SYNTAX Counter64
	MAX-ACCESS read-only
	STATUS current
	DESCRIPTION
		"The total hardware accelerated connections from client-side to the system."
	::= { sysPvaStatEntry 7 } 

sysPvaStatClientCurConns OBJECT-TYPE 
	SYNTAX CounterBasedGauge64
	MAX-ACCESS read-only
	STATUS current
	DESCRIPTION
		"The current hardware accelerated connections from client-side to the system."
	::= { sysPvaStatEntry 8 } 

sysPvaStatServerPktsIn OBJECT-TYPE 
	SYNTAX Counter64
	MAX-ACCESS read-only
	STATUS current
	DESCRIPTION
		"The number of hardware accelerated packets received 
		by the system from server-side."
	::= { sysPvaStatEntry 9 } 

sysPvaStatServerBytesIn OBJECT-TYPE 
	SYNTAX Counter64
	MAX-ACCESS read-only
	STATUS current
	DESCRIPTION
		"The number of hardware accelerated bytes received 
		by the system from server-side."
	::= { sysPvaStatEntry 10 } 

sysPvaStatServerPktsOut OBJECT-TYPE 
	SYNTAX Counter64
	MAX-ACCESS read-only
	STATUS current
	DESCRIPTION
		"The number of hardware accelerated packets sent to server-side from the system."
	::= { sysPvaStatEntry 11 } 

sysPvaStatServerBytesOut OBJECT-TYPE 
	SYNTAX Counter64
	MAX-ACCESS read-only
	STATUS current
	DESCRIPTION
		"The number of hardware accelerated bytes sent to server-side from the system."
	::= { sysPvaStatEntry 12 } 

sysPvaStatServerMaxConns OBJECT-TYPE 
	SYNTAX Counter64
	MAX-ACCESS read-only
	STATUS current
	DESCRIPTION
		"The maximum hardware accelerated connections from server-side to the system."
	::= { sysPvaStatEntry 13 } 

sysPvaStatServerTotConns OBJECT-TYPE 
	SYNTAX Counter64
	MAX-ACCESS read-only
	STATUS current
	DESCRIPTION
		"The total hardware accelerated connections from server-side to the system."
	::= { sysPvaStatEntry 14 } 

sysPvaStatServerCurConns OBJECT-TYPE 
	SYNTAX CounterBasedGauge64
	MAX-ACCESS read-only
	STATUS current
	DESCRIPTION
		"The current hardware accelerated connections from server-side to the system."
	::= { sysPvaStatEntry 15 } 

sysPvaStatTotAssistConns OBJECT-TYPE 
	SYNTAX Counter64
	MAX-ACCESS read-only
	STATUS current
	DESCRIPTION
		"The total number of the partially hardware accelerated connections on the system."
	::= { sysPvaStatEntry 16 } 

sysPvaStatCurAssistConns OBJECT-TYPE 
	SYNTAX CounterBasedGauge64
	MAX-ACCESS read-only
	STATUS current
	DESCRIPTION
		"The current number of the partially hardware accelerated connections on the system."
	::= { sysPvaStatEntry 17 } 

sysPvaStatHardSyncookieGen OBJECT-TYPE 
	SYNTAX Counter64
	MAX-ACCESS read-only
	STATUS current
	DESCRIPTION
		"The number of hardware SYN cookies are generated on the system."
	::= { sysPvaStatEntry 18 } 

sysPvaStatHardSyncookieDet OBJECT-TYPE 
	SYNTAX Counter64
	MAX-ACCESS read-only
	STATUS current
	DESCRIPTION
		"The number of hardware SYN cookies are detected on the system."
	::= { sysPvaStatEntry 19 } 

--==================================================================
-- Tmm_stat
--==================================================================
sysTmmStatResetStats OBJECT-TYPE 
	SYNTAX INTEGER
	MAX-ACCESS read-write
	STATUS current
	DESCRIPTION
		"The action to reset resetable statistics data in  sysTmmStat. 
		 Setting this value to 1 will reset statistics data. 
		 Note, some statistics data may not be reset including data that are incremental counters."
	::= { sysTmmStat 1 } 

sysTmmStatNumber OBJECT-TYPE 
	SYNTAX INTEGER
	MAX-ACCESS read-only
	STATUS current
	DESCRIPTION
		"The number of sysTmmStat entries in the table."
	::= { sysTmmStat 2 } 

sysTmmStatTable OBJECT-TYPE
	SYNTAX SEQUENCE OF SysTmmStatEntry
	MAX-ACCESS not-accessible
	STATUS current
	DESCRIPTION
		"A table containing statistics information of the Traffic Management Module (TMM) on the system."
	::= { sysTmmStat 3 } 

sysTmmStatEntry OBJECT-TYPE
	SYNTAX  SysTmmStatEntry
	MAX-ACCESS not-accessible
	STATUS current
	DESCRIPTION
		"Columns in the sysTmmStat Table"
	INDEX {
		sysTmmStatTmmId
	}
	::= { sysTmmStatTable 1 } 

SysTmmStatEntry ::= 
	SEQUENCE {
        	sysTmmStatTmmId                                        LongDisplayString,
        	sysTmmStatTmmPid                                       Counter64,
        	sysTmmStatCpu                                          Counter64,
        	sysTmmStatTmid                                         Counter64,
        	sysTmmStatNpus                                         Counter64,
        	sysTmmStatClientPktsIn                                 Counter64,
        	sysTmmStatClientBytesIn                                Counter64,
        	sysTmmStatClientPktsOut                                Counter64,
        	sysTmmStatClientBytesOut                               Counter64,
        	sysTmmStatClientMaxConns                               Counter64,
        	sysTmmStatClientTotConns                               Counter64,
        	sysTmmStatClientCurConns                               CounterBasedGauge64,
        	sysTmmStatServerPktsIn                                 Counter64,
        	sysTmmStatServerBytesIn                                Counter64,
        	sysTmmStatServerPktsOut                                Counter64,
        	sysTmmStatServerBytesOut                               Counter64,
        	sysTmmStatServerMaxConns                               Counter64,
        	sysTmmStatServerTotConns                               Counter64,
        	sysTmmStatServerCurConns                               CounterBasedGauge64,
        	sysTmmStatMaintenanceModeDeny                          Counter64,
        	sysTmmStatMaxConnVirtualAddrDeny                       Counter64,
        	sysTmmStatMaxConnVirtualPathDeny                       Counter64,
        	sysTmmStatVirtualServerNonSynDeny                      Counter64,
        	sysTmmStatNoHandlerDeny                                Counter64,
        	sysTmmStatLicenseDeny                                  Counter64,
        	sysTmmStatCmpConnRedirected                            Counter64,
        	sysTmmStatConnectionMemoryErrors                       Counter64,
        	sysTmmStatTmTotalCycles                                Counter64,
        	sysTmmStatTmIdleCycles                                 Counter64,
        	sysTmmStatTmSleepCycles                                Counter64,
        	sysTmmStatMemoryTotal                                  CounterBasedGauge64,
        	sysTmmStatMemoryUsed                                   CounterBasedGauge64,
        	sysTmmStatDroppedPackets                               Counter64,
        	sysTmmStatIncomingPacketErrors                         Counter64,
        	sysTmmStatOutgoingPacketErrors                         Counter64,
        	sysTmmStatHttpRequests                                 Counter64,
        	sysTmmStatTmUsageRatio5s                               CounterBasedGauge64,
        	sysTmmStatTmUsageRatio1m                               CounterBasedGauge64,
        	sysTmmStatTmUsageRatio5m                               CounterBasedGauge64,
        	sysTmmStatSlotId                                       Counter64,
        	sysTmmStatMemoryTotalKb                                CounterBasedGauge64,
        	sysTmmStatMemoryUsedKb                                 CounterBasedGauge64
	}

sysTmmStatTmmId OBJECT-TYPE 
	SYNTAX LongDisplayString
	MAX-ACCESS read-only
	STATUS current
	DESCRIPTION
		"The key for TMM (Traffic Management Module) access on the system. 
		This is a concatenation of the slot and cpuid. ie: '1.0'."
	::= { sysTmmStatEntry 1 } 

sysTmmStatTmmPid OBJECT-TYPE 
	SYNTAX Counter64
	MAX-ACCESS read-only
	STATUS current
	DESCRIPTION
		"The process ID of the specified TMM (Traffic Management Module) on the system."
	::= { sysTmmStatEntry 2 } 

sysTmmStatCpu OBJECT-TYPE 
	SYNTAX Counter64
	MAX-ACCESS read-only
	STATUS current
	DESCRIPTION
		"An index of CPU on which the specified TMM (Traffic Management Module) is running on the system."
	::= { sysTmmStatEntry 3 } 

sysTmmStatTmid OBJECT-TYPE 
	SYNTAX Counter64
	MAX-ACCESS read-only
	STATUS current
	DESCRIPTION
		"An index of a running TMM (Traffic Management Module) on the system."
	::= { sysTmmStatEntry 4 } 

sysTmmStatNpus OBJECT-TYPE 
	SYNTAX Counter64
	MAX-ACCESS read-only
	STATUS current
	DESCRIPTION
		"The number of TMMs (Traffic Management Module) on the system."
	::= { sysTmmStatEntry 5 } 

sysTmmStatClientPktsIn OBJECT-TYPE 
	SYNTAX Counter64
	MAX-ACCESS read-only
	STATUS current
	DESCRIPTION
		"The number of packets received by the system from client-side."
	::= { sysTmmStatEntry 6 } 

sysTmmStatClientBytesIn OBJECT-TYPE 
	SYNTAX Counter64
	MAX-ACCESS read-only
	STATUS current
	DESCRIPTION
		"The number of bytes received by the system from client-side."
	::= { sysTmmStatEntry 7 } 

sysTmmStatClientPktsOut OBJECT-TYPE 
	SYNTAX Counter64
	MAX-ACCESS read-only
	STATUS current
	DESCRIPTION
		"The number of packets sent to client-side from the system."
	::= { sysTmmStatEntry 8 } 

sysTmmStatClientBytesOut OBJECT-TYPE 
	SYNTAX Counter64
	MAX-ACCESS read-only
	STATUS current
	DESCRIPTION
		"The number of bytes sent to client-side from the system."
	::= { sysTmmStatEntry 9 } 

sysTmmStatClientMaxConns OBJECT-TYPE 
	SYNTAX Counter64
	MAX-ACCESS read-only
	STATUS current
	DESCRIPTION
		"The maximum connections from client-side to the system."
	::= { sysTmmStatEntry 10 } 

sysTmmStatClientTotConns OBJECT-TYPE 
	SYNTAX Counter64
	MAX-ACCESS read-only
	STATUS current
	DESCRIPTION
		"The total connections from client-side to the system."
	::= { sysTmmStatEntry 11 } 

sysTmmStatClientCurConns OBJECT-TYPE 
	SYNTAX CounterBasedGauge64
	MAX-ACCESS read-only
	STATUS current
	DESCRIPTION
		"The current connections from client-side to the system."
	::= { sysTmmStatEntry 12 } 

sysTmmStatServerPktsIn OBJECT-TYPE 
	SYNTAX Counter64
	MAX-ACCESS read-only
	STATUS current
	DESCRIPTION
		"The number of packets received by the system from server-side."
	::= { sysTmmStatEntry 13 } 

sysTmmStatServerBytesIn OBJECT-TYPE 
	SYNTAX Counter64
	MAX-ACCESS read-only
	STATUS current
	DESCRIPTION
		"The number of bytes received by the system from server-side."
	::= { sysTmmStatEntry 14 } 

sysTmmStatServerPktsOut OBJECT-TYPE 
	SYNTAX Counter64
	MAX-ACCESS read-only
	STATUS current
	DESCRIPTION
		"The number of packets sent to server-side from the system."
	::= { sysTmmStatEntry 15 } 

sysTmmStatServerBytesOut OBJECT-TYPE 
	SYNTAX Counter64
	MAX-ACCESS read-only
	STATUS current
	DESCRIPTION
		"The number of bytes sent to server-side from the system."
	::= { sysTmmStatEntry 16 } 

sysTmmStatServerMaxConns OBJECT-TYPE 
	SYNTAX Counter64
	MAX-ACCESS read-only
	STATUS current
	DESCRIPTION
		"The maximum connections from server-side to the system."
	::= { sysTmmStatEntry 17 } 

sysTmmStatServerTotConns OBJECT-TYPE 
	SYNTAX Counter64
	MAX-ACCESS read-only
	STATUS current
	DESCRIPTION
		"The total connections from server-side to the system."
	::= { sysTmmStatEntry 18 } 

sysTmmStatServerCurConns OBJECT-TYPE 
	SYNTAX CounterBasedGauge64
	MAX-ACCESS read-only
	STATUS current
	DESCRIPTION
		"The current connections from server-side to the system."
	::= { sysTmmStatEntry 19 } 

sysTmmStatMaintenanceModeDeny OBJECT-TYPE 
	SYNTAX Counter64
	MAX-ACCESS read-only
	STATUS current
	DESCRIPTION
		"The connection requests rejected because the virtual
		server was in maintenance mode. "
	::= { sysTmmStatEntry 20 } 

sysTmmStatMaxConnVirtualAddrDeny OBJECT-TYPE 
	SYNTAX Counter64
	MAX-ACCESS read-only
	STATUS current
	DESCRIPTION
		"The connection requests rejected because they exceeded
		the connection limit for a virtual server address."
	::= { sysTmmStatEntry 21 } 

sysTmmStatMaxConnVirtualPathDeny OBJECT-TYPE 
	SYNTAX Counter64
	MAX-ACCESS read-only
	STATUS current
	DESCRIPTION
		"The connection requests rejected because they exceeded
		the connection limit for a virtual server (IP:port)."
	::= { sysTmmStatEntry 22 } 

sysTmmStatVirtualServerNonSynDeny OBJECT-TYPE 
	SYNTAX Counter64
	MAX-ACCESS read-only
	STATUS current
	DESCRIPTION
		"The packets that are not connection requests and are 
		destined for a virtual server that has no connection 
		for the client address."
	::= { sysTmmStatEntry 23 } 

sysTmmStatNoHandlerDeny OBJECT-TYPE 
	SYNTAX Counter64
	MAX-ACCESS read-only
	STATUS current
	DESCRIPTION
		"The incoming packets that could not be processed by a
		a virtual server, NAT, or SNAT."
	::= { sysTmmStatEntry 24 } 

sysTmmStatLicenseDeny OBJECT-TYPE 
	SYNTAX Counter64
	MAX-ACCESS read-only
	STATUS current
	DESCRIPTION
		"The packets which were dropped due to exceeding licensing 
		limitations."
	::= { sysTmmStatEntry 25 } 

sysTmmStatCmpConnRedirected OBJECT-TYPE 
	SYNTAX Counter64
	MAX-ACCESS read-only
	STATUS current
	DESCRIPTION
		"The connections that were redirected to a different TMM in the cluster."
	::= { sysTmmStatEntry 26 } 

sysTmmStatConnectionMemoryErrors OBJECT-TYPE 
	SYNTAX Counter64
	MAX-ACCESS read-only
	STATUS current
	DESCRIPTION
		"The connections could not be created because memory was not available."
	::= { sysTmmStatEntry 27 } 

sysTmmStatTmTotalCycles OBJECT-TYPE 
	SYNTAX Counter64
	MAX-ACCESS read-only
	STATUS	 deprecated
	DESCRIPTION
		"Deprecated! Please use the provided tmm usage ratios.
			Traffic management CPU usage. The total cycles spent in traffic management."
	::= { sysTmmStatEntry 28 } 

sysTmmStatTmIdleCycles OBJECT-TYPE 
	SYNTAX Counter64
	MAX-ACCESS read-only
	STATUS	 deprecated
	DESCRIPTION
		"Deprecated! Please use the provided tmm usage ratios.
		Traffic management CPU usage. The cycles spent polling with no traffic."
	::= { sysTmmStatEntry 29 } 

sysTmmStatTmSleepCycles OBJECT-TYPE 
	SYNTAX Counter64
	MAX-ACCESS read-only
	STATUS	 deprecated
	DESCRIPTION
		"Deprecated! Please use the provided tmm usage ratios.
		Traffic management CPU usage. The cycles yielded (uniprocessor only)."
	::= { sysTmmStatEntry 30 } 

sysTmmStatMemoryTotal OBJECT-TYPE 
	SYNTAX CounterBasedGauge64
	MAX-ACCESS read-only
	STATUS current
	DESCRIPTION
		"The total memory available in bytes for TMM (Traffic Management Module)."
	::= { sysTmmStatEntry 31 } 

sysTmmStatMemoryUsed OBJECT-TYPE 
	SYNTAX CounterBasedGauge64
	MAX-ACCESS read-only
	STATUS current
	DESCRIPTION
		"The memory in use in bytes for TMM (Traffic Management Module)."
	::= { sysTmmStatEntry 32 } 

sysTmmStatDroppedPackets OBJECT-TYPE 
	SYNTAX Counter64
	MAX-ACCESS read-only
	STATUS current
	DESCRIPTION
		"The total dropped packets."
	::= { sysTmmStatEntry 33 } 

sysTmmStatIncomingPacketErrors OBJECT-TYPE 
	SYNTAX Counter64
	MAX-ACCESS read-only
	STATUS current
	DESCRIPTION
		"The total incoming packet errors for the system."
	::= { sysTmmStatEntry 34 } 

sysTmmStatOutgoingPacketErrors OBJECT-TYPE 
	SYNTAX Counter64
	MAX-ACCESS read-only
	STATUS current
	DESCRIPTION
		"The total outgoing packet errors for the system."
	::= { sysTmmStatEntry 35 } 

sysTmmStatHttpRequests OBJECT-TYPE 
	SYNTAX Counter64
	MAX-ACCESS read-only
	STATUS current
	DESCRIPTION
		"The total number of HTTP requests to the system."
	::= { sysTmmStatEntry 36 } 

sysTmmStatTmUsageRatio5s OBJECT-TYPE 
	SYNTAX CounterBasedGauge64
	MAX-ACCESS read-only
	STATUS current
	DESCRIPTION
		"The percentage of time the TMM was busy over the last 5 seconds."
	::= { sysTmmStatEntry 37 } 

sysTmmStatTmUsageRatio1m OBJECT-TYPE 
	SYNTAX CounterBasedGauge64
	MAX-ACCESS read-only
	STATUS current
	DESCRIPTION
		"The percentage of time the TMM was busy over the last 1 minute."
	::= { sysTmmStatEntry 38 } 

sysTmmStatTmUsageRatio5m OBJECT-TYPE 
	SYNTAX CounterBasedGauge64
	MAX-ACCESS read-only
	STATUS current
	DESCRIPTION
		"The percentage of time the TMM was busy over the last 5 minutes."
	::= { sysTmmStatEntry 39 } 

sysTmmStatSlotId OBJECT-TYPE 
	SYNTAX Counter64
	MAX-ACCESS read-only
	STATUS current
	DESCRIPTION
		"The index of the slot where the TMM is running."
	::= { sysTmmStatEntry 40 } 

sysTmmStatMemoryTotalKb OBJECT-TYPE 
	SYNTAX CounterBasedGauge64
	MAX-ACCESS read-only
	STATUS current
	DESCRIPTION
		"The total memory available in Kilobytes for TMM (Traffic Management Module)."
	::= { sysTmmStatEntry 41 } 

sysTmmStatMemoryUsedKb OBJECT-TYPE 
	SYNTAX CounterBasedGauge64
	MAX-ACCESS read-only
	STATUS current
	DESCRIPTION
		"The memory in use in Kilobytes for TMM (Traffic Management Module)."
	::= { sysTmmStatEntry 42 } 

--==================================================================
-- Host_info_stat
--==================================================================
sysMultiHostNumber OBJECT-TYPE 
	SYNTAX INTEGER
	MAX-ACCESS read-only
	STATUS current
	DESCRIPTION
		"The number of sysMultiHost entries in the table."
	::= { sysMultiHost 1 } 

sysMultiHostTable OBJECT-TYPE
	SYNTAX SEQUENCE OF SysMultiHostEntry
	MAX-ACCESS not-accessible
	STATUS current
	DESCRIPTION
		"A table containing system statistics information of the host, such as memory usage, cpu type, etc."
	::= { sysMultiHost 2 } 

sysMultiHostEntry OBJECT-TYPE
	SYNTAX  SysMultiHostEntry
	MAX-ACCESS not-accessible
	STATUS current
	DESCRIPTION
		"Columns in the sysMultiHost Table"
	INDEX {
		sysMultiHostHostId
	}
	::= { sysMultiHostTable 1 } 

SysMultiHostEntry ::= 
	SEQUENCE {
        	sysMultiHostHostId                                     LongDisplayString,
        	sysMultiHostTotal                                      CounterBasedGauge64,
        	sysMultiHostUsed                                       CounterBasedGauge64,
        	sysMultiHostMode                                       INTEGER,
        	sysMultiHostCpuCount                                   Counter64,
        	sysMultiHostActiveCpuCount                             Counter64
	}

sysMultiHostHostId OBJECT-TYPE 
	SYNTAX LongDisplayString
	MAX-ACCESS read-only
	STATUS current
	DESCRIPTION
		"The host identifier."
	::= { sysMultiHostEntry 1 } 

sysMultiHostTotal OBJECT-TYPE 
	SYNTAX CounterBasedGauge64
	MAX-ACCESS read-only
	STATUS current
	DESCRIPTION
		"The total host memory in bytes for the specified host."
	::= { sysMultiHostEntry 2 } 

sysMultiHostUsed OBJECT-TYPE 
	SYNTAX CounterBasedGauge64
	MAX-ACCESS read-only
	STATUS current
	DESCRIPTION
		"The host memory in bytes currently in use for the specified host."
	::= { sysMultiHostEntry 3 } 

sysMultiHostMode OBJECT-TYPE 
	SYNTAX INTEGER {
		modeup(0),
		modesmp(1)
	}
	MAX-ACCESS read-only
	STATUS	 deprecated
	DESCRIPTION
		"Deprecated! This used to reference mode processor was running in."
	::= { sysMultiHostEntry 4 } 

sysMultiHostCpuCount OBJECT-TYPE 
	SYNTAX Counter64
	MAX-ACCESS read-only
	STATUS current
	DESCRIPTION
		"The number of CPUs for the specified host."
	::= { sysMultiHostEntry 5 } 

sysMultiHostActiveCpuCount OBJECT-TYPE 
	SYNTAX Counter64
	MAX-ACCESS read-only
	STATUS current
	DESCRIPTION
		"The number of active CPUs for the specified host."
	::= { sysMultiHostEntry 6 } 

--==================================================================
-- Host_info_stat_cpu_info
--==================================================================
sysMultiHostCpuNumber OBJECT-TYPE 
	SYNTAX INTEGER
	MAX-ACCESS read-only
	STATUS current
	DESCRIPTION
		"The number of sysMultiHostCpu entries in the table."
	::= { sysMultiHostCpu 1 } 

sysMultiHostCpuTable OBJECT-TYPE
	SYNTAX SEQUENCE OF SysMultiHostCpuEntry
	MAX-ACCESS not-accessible
	STATUS current
	DESCRIPTION
		"A table containing entries of system CPU usage information for a system."
	::= { sysMultiHostCpu 2 } 

sysMultiHostCpuEntry OBJECT-TYPE
	SYNTAX  SysMultiHostCpuEntry
	MAX-ACCESS not-accessible
	STATUS current
	DESCRIPTION
		"Columns in the sysMultiHostCpu Table"
	INDEX {
		sysMultiHostCpuHostId,
		sysMultiHostCpuIndex
	}
	::= { sysMultiHostCpuTable 1 } 

SysMultiHostCpuEntry ::= 
	SEQUENCE {
        	sysMultiHostCpuHostId                                  LongDisplayString,
        	sysMultiHostCpuIndex                                   INTEGER,
        	sysMultiHostCpuId                                      Integer32,
        	sysMultiHostCpuUser                                    Counter64,
        	sysMultiHostCpuNice                                    Counter64,
        	sysMultiHostCpuSystem                                  Counter64,
        	sysMultiHostCpuIdle                                    Counter64,
        	sysMultiHostCpuIrq                                     Counter64,
        	sysMultiHostCpuSoftirq                                 Counter64,
        	sysMultiHostCpuIowait                                  Counter64,
        	sysMultiHostCpuUsageRatio                              CounterBasedGauge64,
        	sysMultiHostCpuUser5s                                  CounterBasedGauge64,
        	sysMultiHostCpuNice5s                                  CounterBasedGauge64,
        	sysMultiHostCpuSystem5s                                CounterBasedGauge64,
        	sysMultiHostCpuIdle5s                                  CounterBasedGauge64,
        	sysMultiHostCpuIrq5s                                   CounterBasedGauge64,
        	sysMultiHostCpuSoftirq5s                               CounterBasedGauge64,
        	sysMultiHostCpuIowait5s                                CounterBasedGauge64,
        	sysMultiHostCpuUsageRatio5s                            CounterBasedGauge64,
        	sysMultiHostCpuUser1m                                  CounterBasedGauge64,
        	sysMultiHostCpuNice1m                                  CounterBasedGauge64,
        	sysMultiHostCpuSystem1m                                CounterBasedGauge64,
        	sysMultiHostCpuIdle1m                                  CounterBasedGauge64,
        	sysMultiHostCpuIrq1m                                   CounterBasedGauge64,
        	sysMultiHostCpuSoftirq1m                               CounterBasedGauge64,
        	sysMultiHostCpuIowait1m                                CounterBasedGauge64,
        	sysMultiHostCpuUsageRatio1m                            CounterBasedGauge64,
        	sysMultiHostCpuUser5m                                  CounterBasedGauge64,
        	sysMultiHostCpuNice5m                                  CounterBasedGauge64,
        	sysMultiHostCpuSystem5m                                CounterBasedGauge64,
        	sysMultiHostCpuIdle5m                                  CounterBasedGauge64,
        	sysMultiHostCpuIrq5m                                   CounterBasedGauge64,
        	sysMultiHostCpuSoftirq5m                               CounterBasedGauge64,
        	sysMultiHostCpuIowait5m                                CounterBasedGauge64,
        	sysMultiHostCpuUsageRatio5m                            CounterBasedGauge64,
        	sysMultiHostCpuStolen                                  CounterBasedGauge64,
        	sysMultiHostCpuStolen5s                                CounterBasedGauge64,
        	sysMultiHostCpuStolen1m                                CounterBasedGauge64,
        	sysMultiHostCpuStolen5m                                CounterBasedGauge64,
        	sysMultiHostCpuSlotId                                  Integer32
	}

sysMultiHostCpuHostId OBJECT-TYPE 
	SYNTAX LongDisplayString
	MAX-ACCESS read-only
	STATUS current
	DESCRIPTION
		"A host identifier on the system."
	::= { sysMultiHostCpuEntry 1 } 

sysMultiHostCpuIndex OBJECT-TYPE 
	SYNTAX INTEGER(1..2147483647)
	MAX-ACCESS read-only
	STATUS current
	DESCRIPTION
		"The index of the table that contains the information of 
		the specified processor of the associated host."
	::= { sysMultiHostCpuEntry 2 } 

sysMultiHostCpuId OBJECT-TYPE 
	SYNTAX Integer32
	MAX-ACCESS read-only
	STATUS current
	DESCRIPTION
		"The ID of the specified processor of the associated host."
	::= { sysMultiHostCpuEntry 3 } 

sysMultiHostCpuUser OBJECT-TYPE 
	SYNTAX Counter64
	MAX-ACCESS read-only
	STATUS current
	DESCRIPTION
		"The time spent by the specified processor in user context for the associated host."
	::= { sysMultiHostCpuEntry 4 } 

sysMultiHostCpuNice OBJECT-TYPE 
	SYNTAX Counter64
	MAX-ACCESS read-only
	STATUS current
	DESCRIPTION
		"The time spent by the specified processor running niced processes for the associated host."
	::= { sysMultiHostCpuEntry 5 } 

sysMultiHostCpuSystem OBJECT-TYPE 
	SYNTAX Counter64
	MAX-ACCESS read-only
	STATUS current
	DESCRIPTION
		"The time spent by the specified processor servicing system calls for the associated host."
	::= { sysMultiHostCpuEntry 6 } 

sysMultiHostCpuIdle OBJECT-TYPE 
	SYNTAX Counter64
	MAX-ACCESS read-only
	STATUS current
	DESCRIPTION
		"The time spent by the specified processor doing nothing for the associated host."
	::= { sysMultiHostCpuEntry 7 } 

sysMultiHostCpuIrq OBJECT-TYPE 
	SYNTAX Counter64
	MAX-ACCESS read-only
	STATUS current
	DESCRIPTION
		"The time spent by the specified processor servicing hardware interrupts for the associated host."
	::= { sysMultiHostCpuEntry 8 } 

sysMultiHostCpuSoftirq OBJECT-TYPE 
	SYNTAX Counter64
	MAX-ACCESS read-only
	STATUS current
	DESCRIPTION
		"The time spent by the specified processor servicing soft interrupts for the associated host."
	::= { sysMultiHostCpuEntry 9 } 

sysMultiHostCpuIowait OBJECT-TYPE 
	SYNTAX Counter64
	MAX-ACCESS read-only
	STATUS current
	DESCRIPTION
		"The time spent by the specified processor waiting for external I/O to complete for the associated host."
	::= { sysMultiHostCpuEntry 10 } 

sysMultiHostCpuUsageRatio OBJECT-TYPE 
	SYNTAX CounterBasedGauge64
	MAX-ACCESS read-only
	STATUS current
	DESCRIPTION
		"This is usage ratio of CPU for the associated host. This value indicates the present cpu usage. For usage
			computed over specific intervals, please use the specific (5s,1m,5m) OIDs"
	::= { sysMultiHostCpuEntry 11 } 

sysMultiHostCpuUser5s OBJECT-TYPE 
	SYNTAX CounterBasedGauge64
	MAX-ACCESS read-only
	STATUS current
	DESCRIPTION
		"The average time spent by the specified processor in user context for the associated host in the last five seconds."
	::= { sysMultiHostCpuEntry 12 } 

sysMultiHostCpuNice5s OBJECT-TYPE 
	SYNTAX CounterBasedGauge64
	MAX-ACCESS read-only
	STATUS current
	DESCRIPTION
		"The average time spent by the specified processor running niced processes for the associated host in the last five seconds."
	::= { sysMultiHostCpuEntry 13 } 

sysMultiHostCpuSystem5s OBJECT-TYPE 
	SYNTAX CounterBasedGauge64
	MAX-ACCESS read-only
	STATUS current
	DESCRIPTION
		"The average time spent by the specified processor servicing system calls for the associated host in the last five seconds."
	::= { sysMultiHostCpuEntry 14 } 

sysMultiHostCpuIdle5s OBJECT-TYPE 
	SYNTAX CounterBasedGauge64
	MAX-ACCESS read-only
	STATUS current
	DESCRIPTION
		"The average time spent by the specified processor doing nothing for the associated host in the last five seconds."
	::= { sysMultiHostCpuEntry 15 } 

sysMultiHostCpuIrq5s OBJECT-TYPE 
	SYNTAX CounterBasedGauge64
	MAX-ACCESS read-only
	STATUS current
	DESCRIPTION
		"The average time spent by the specified processor servicing hardware interrupts for the associated host in the last five seconds."
	::= { sysMultiHostCpuEntry 16 } 

sysMultiHostCpuSoftirq5s OBJECT-TYPE 
	SYNTAX CounterBasedGauge64
	MAX-ACCESS read-only
	STATUS current
	DESCRIPTION
		"The average time spent by the specified processor servicing soft interrupts for the associated host in the last five seconds."
	::= { sysMultiHostCpuEntry 17 } 

sysMultiHostCpuIowait5s OBJECT-TYPE 
	SYNTAX CounterBasedGauge64
	MAX-ACCESS read-only
	STATUS current
	DESCRIPTION
		"The average time spent by the specified processor waiting for external I/O to complete for the associated host in the last five seconds."
	::= { sysMultiHostCpuEntry 18 } 

sysMultiHostCpuUsageRatio5s OBJECT-TYPE 
	SYNTAX CounterBasedGauge64
	MAX-ACCESS read-only
	STATUS current
	DESCRIPTION
		"This is  average usage ratio of CPU for the associated host in the last five seconds. It is calculated by 
		(sum of deltas for user, niced, system)/(sum of deltas of user, niced, system, idle, irq, softirq, and iowait),
		where each delta is the difference for each stat over the last 5-second interval;
		user: sysMultiHostCpuUser5s;
		niced: sysMultiHostCpuNiced5s;
			stolen: sysMultiHostCpuStolen5s;
		system: sysMultiHostCpuSystem5s;
		idle: sysMultiHostCpuIdle5s;
		irq: sysMultiHostCpuIrq5s;
		iowait: sysMultiHostCpuIowait5s"
	::= { sysMultiHostCpuEntry 19 } 

sysMultiHostCpuUser1m OBJECT-TYPE 
	SYNTAX CounterBasedGauge64
	MAX-ACCESS read-only
	STATUS current
	DESCRIPTION
		"The average time spent by the specified processor in user context for the associated host in the last one minute."
	::= { sysMultiHostCpuEntry 20 } 

sysMultiHostCpuNice1m OBJECT-TYPE 
	SYNTAX CounterBasedGauge64
	MAX-ACCESS read-only
	STATUS current
	DESCRIPTION
		"The average time spent by the specified processor running niced processes for the associated host in the last one minute."
	::= { sysMultiHostCpuEntry 21 } 

sysMultiHostCpuSystem1m OBJECT-TYPE 
	SYNTAX CounterBasedGauge64
	MAX-ACCESS read-only
	STATUS current
	DESCRIPTION
		"The average time spent by the specified processor servicing system calls for the associated host in the last one minute."
	::= { sysMultiHostCpuEntry 22 } 

sysMultiHostCpuIdle1m OBJECT-TYPE 
	SYNTAX CounterBasedGauge64
	MAX-ACCESS read-only
	STATUS current
	DESCRIPTION
		"The average time spent by the specified processor doing nothing for the associated host in the last one minute."
	::= { sysMultiHostCpuEntry 23 } 

sysMultiHostCpuIrq1m OBJECT-TYPE 
	SYNTAX CounterBasedGauge64
	MAX-ACCESS read-only
	STATUS current
	DESCRIPTION
		"The average time spent by the specified processor servicing hardware interrupts for the associated host in the last one minute."
	::= { sysMultiHostCpuEntry 24 } 

sysMultiHostCpuSoftirq1m OBJECT-TYPE 
	SYNTAX CounterBasedGauge64
	MAX-ACCESS read-only
	STATUS current
	DESCRIPTION
		"The average time spent by the specified processor servicing soft interrupts for the associated host in the last one minute."
	::= { sysMultiHostCpuEntry 25 } 

sysMultiHostCpuIowait1m OBJECT-TYPE 
	SYNTAX CounterBasedGauge64
	MAX-ACCESS read-only
	STATUS current
	DESCRIPTION
		"The average time spent by the specified processor waiting for external I/O to complete for the associated host in the last one minute."
	::= { sysMultiHostCpuEntry 26 } 

sysMultiHostCpuUsageRatio1m OBJECT-TYPE 
	SYNTAX CounterBasedGauge64
	MAX-ACCESS read-only
	STATUS current
	DESCRIPTION
		"This is  average usage ratio of CPU for the associated host in the last one minute. It is calculated by 
		(sum of deltas for user, niced, system)/(sum of deltas of user, niced, system, idle, irq, softirq, and iowait),
		where each delta is the difference for each stat over the last 1-minute interval;
		user: sysMultiHostCpuUser1m;
		niced: sysMultiHostCpuNiced1m;
			stolen: sysMultiHostCpuStolen1m;
		system: sysMultiHostCpuSystem1m;
		idle: sysMultiHostCpuIdle1m;
		irq: sysMultiHostCpuIrq1m;
		iowait: sysMultiHostCpuIowait1m"
	::= { sysMultiHostCpuEntry 27 } 

sysMultiHostCpuUser5m OBJECT-TYPE 
	SYNTAX CounterBasedGauge64
	MAX-ACCESS read-only
	STATUS current
	DESCRIPTION
		"The average time spent by the specified processor in user context for the associated host in the last five minutes."
	::= { sysMultiHostCpuEntry 28 } 

sysMultiHostCpuNice5m OBJECT-TYPE 
	SYNTAX CounterBasedGauge64
	MAX-ACCESS read-only
	STATUS current
	DESCRIPTION
		"The average time spent by the specified processor running niced processes for the associated host in the last five minutes."
	::= { sysMultiHostCpuEntry 29 } 

sysMultiHostCpuSystem5m OBJECT-TYPE 
	SYNTAX CounterBasedGauge64
	MAX-ACCESS read-only
	STATUS current
	DESCRIPTION
		"The average time spent by the specified processor servicing system calls for the associated host in the last five minutes."
	::= { sysMultiHostCpuEntry 30 } 

sysMultiHostCpuIdle5m OBJECT-TYPE 
	SYNTAX CounterBasedGauge64
	MAX-ACCESS read-only
	STATUS current
	DESCRIPTION
		"The average time spent by the specified processor doing nothing for the associated host in the last five minutes."
	::= { sysMultiHostCpuEntry 31 } 

sysMultiHostCpuIrq5m OBJECT-TYPE 
	SYNTAX CounterBasedGauge64
	MAX-ACCESS read-only
	STATUS current
	DESCRIPTION
		"The average time spent by the specified processor servicing hardware interrupts for the associated host in the last five minutes."
	::= { sysMultiHostCpuEntry 32 } 

sysMultiHostCpuSoftirq5m OBJECT-TYPE 
	SYNTAX CounterBasedGauge64
	MAX-ACCESS read-only
	STATUS current
	DESCRIPTION
		"The average time spent by the specified processor servicing soft interrupts for the associated host in the last five minutes."
	::= { sysMultiHostCpuEntry 33 } 

sysMultiHostCpuIowait5m OBJECT-TYPE 
	SYNTAX CounterBasedGauge64
	MAX-ACCESS read-only
	STATUS current
	DESCRIPTION
		"The average time spent by the specified processor waiting for external I/O to complete for the associated host in the last five minutes."
	::= { sysMultiHostCpuEntry 34 } 

sysMultiHostCpuUsageRatio5m OBJECT-TYPE 
	SYNTAX CounterBasedGauge64
	MAX-ACCESS read-only
	STATUS current
	DESCRIPTION
		"This is  average usage ratio of CPU for the associated host in the last five minutes. It is calculated by 
		(sum of deltas for user, niced, system)/(sum of deltas of user, niced, system, idle, irq, softirq, and iowait),
		where each delta is the difference for each stat over the last 5-minute interval;
		user: sysMultiHostCpuUser5m;
		niced: sysMultiHostCpuNiced5m;
			stolen: sysMultiHostCpuStolen5m;
		system: sysMultiHostCpuSystem5m;
		idle: sysMultiHostCpuIdle5m;
		irq: sysMultiHostCpuIrq5m;
		iowait: sysMultiHostCpuIowait5m"
	::= { sysMultiHostCpuEntry 35 } 

sysMultiHostCpuStolen OBJECT-TYPE 
	SYNTAX CounterBasedGauge64
	MAX-ACCESS read-only
	STATUS current
	DESCRIPTION
		"The time 'stolen' from the specified processor for the associated host."
	::= { sysMultiHostCpuEntry 36 } 

sysMultiHostCpuStolen5s OBJECT-TYPE 
	SYNTAX CounterBasedGauge64
	MAX-ACCESS read-only
	STATUS current
	DESCRIPTION
		"The average time 'stolen' from the specified processor for the associated host in the last five seconds."
	::= { sysMultiHostCpuEntry 37 } 

sysMultiHostCpuStolen1m OBJECT-TYPE 
	SYNTAX CounterBasedGauge64
	MAX-ACCESS read-only
	STATUS current
	DESCRIPTION
		"The average time 'stolen' from the specified processor for the associated host in the last one minute."
	::= { sysMultiHostCpuEntry 38 } 

sysMultiHostCpuStolen5m OBJECT-TYPE 
	SYNTAX CounterBasedGauge64
	MAX-ACCESS read-only
	STATUS current
	DESCRIPTION
		"The average time 'stolen' from the specified processor for the associated host in the last five minutes."
	::= { sysMultiHostCpuEntry 39 } 

sysMultiHostCpuSlotId OBJECT-TYPE 
	SYNTAX Integer32
	MAX-ACCESS read-only
	STATUS current
	DESCRIPTION
		"If this is an appliance, the slot is 0. If this is in a cluster, the slot is the position in the cluster (1-based)"
	::= { sysMultiHostCpuEntry 40 } 

--==================================================================
-- Global_bigproto_stat
--==================================================================
sysFastL4StatResetStats OBJECT-TYPE 
	SYNTAX INTEGER
	MAX-ACCESS read-write
	STATUS current
	DESCRIPTION
		"The action to reset resetable statistics data in  sysGlobalFastL4Stat. 
		 Setting this value to 1 will reset statistics data. 
		 Note, some statistics data may not be reset including data that are incremental counters."
	::= { sysGlobalFastL4Stat 1 } 

sysFastL4StatOpen OBJECT-TYPE 
	SYNTAX Integer32
	MAX-ACCESS read-only
	STATUS current
	DESCRIPTION
		"The total number of current open connections."
	::= { sysGlobalFastL4Stat 2 } 

sysFastL4StatAccepts OBJECT-TYPE 
	SYNTAX Counter64
	MAX-ACCESS read-only
	STATUS current
	DESCRIPTION
		"The total number of accepted connections."
	::= { sysGlobalFastL4Stat 3 } 

sysFastL4StatAcceptfails OBJECT-TYPE 
	SYNTAX Counter64
	MAX-ACCESS read-only
	STATUS current
	DESCRIPTION
		"The total number of not accepted connections."
	::= { sysGlobalFastL4Stat 4 } 

sysFastL4StatExpires OBJECT-TYPE 
	SYNTAX Counter64
	MAX-ACCESS read-only
	STATUS current
	DESCRIPTION
		"The total number of expired connections due to idle timeout."
	::= { sysGlobalFastL4Stat 5 } 

sysFastL4StatRxbadpkt OBJECT-TYPE 
	SYNTAX Counter64
	MAX-ACCESS read-only
	STATUS current
	DESCRIPTION
		"The total number of malformed packets."
	::= { sysGlobalFastL4Stat 6 } 

sysFastL4StatRxunreach OBJECT-TYPE 
	SYNTAX Counter64
	MAX-ACCESS read-only
	STATUS current
	DESCRIPTION
		"The total number of received ICMP unreach/TCP RST."
	::= { sysGlobalFastL4Stat 7 } 

sysFastL4StatRxbadunreach OBJECT-TYPE 
	SYNTAX Counter64
	MAX-ACCESS read-only
	STATUS current
	DESCRIPTION
		"The total number of received TCP RST outside the current window."
	::= { sysGlobalFastL4Stat 8 } 

sysFastL4StatRxbadsum OBJECT-TYPE 
	SYNTAX Counter64
	MAX-ACCESS read-only
	STATUS current
	DESCRIPTION
		"The total number of bad checksum."
	::= { sysGlobalFastL4Stat 9 } 

sysFastL4StatTxerrors OBJECT-TYPE 
	SYNTAX Counter64
	MAX-ACCESS read-only
	STATUS current
	DESCRIPTION
		"The total number of transmit datagram errors."
	::= { sysGlobalFastL4Stat 10 } 

sysFastL4StatSyncookIssue OBJECT-TYPE 
	SYNTAX Counter64
	MAX-ACCESS read-only
	STATUS current
	DESCRIPTION
		"The total number of syncookies issued."
	::= { sysGlobalFastL4Stat 11 } 

sysFastL4StatSyncookAccept OBJECT-TYPE 
	SYNTAX Counter64
	MAX-ACCESS read-only
	STATUS current
	DESCRIPTION
		"The total number of syncookies accepted."
	::= { sysGlobalFastL4Stat 12 } 

sysFastL4StatSyncookReject OBJECT-TYPE 
	SYNTAX Counter64
	MAX-ACCESS read-only
	STATUS current
	DESCRIPTION
		"The total number of syncookies rejected."
	::= { sysGlobalFastL4Stat 13 } 

sysFastL4StatServersynrtx OBJECT-TYPE 
	SYNTAX Counter64
	MAX-ACCESS read-only
	STATUS current
	DESCRIPTION
		"The total number of retransmissions of SYN to server for a syncookied connection."
	::= { sysGlobalFastL4Stat 14 } 

--==================================================================
-- Cluster
--==================================================================
sysClusterNumber OBJECT-TYPE 
	SYNTAX INTEGER
	MAX-ACCESS read-only
	STATUS current
	DESCRIPTION
		"The number of sysCluster entries in the table."
	::= { sysCluster 1 } 

sysClusterTable OBJECT-TYPE
	SYNTAX SEQUENCE OF SysClusterEntry
	MAX-ACCESS not-accessible
	STATUS current
	DESCRIPTION
		"A table containing cluster information of the system."
	::= { sysCluster 2 } 

sysClusterEntry OBJECT-TYPE
	SYNTAX  SysClusterEntry
	MAX-ACCESS not-accessible
	STATUS current
	DESCRIPTION
		"Columns in the sysCluster Table"
	INDEX {
		sysClusterName
	}
	::= { sysClusterTable 1 } 

SysClusterEntry ::= 
	SEQUENCE {
        	sysClusterName                                         LongDisplayString,
        	sysClusterEnabled                                      INTEGER,
        	sysClusterFloatMgmtIpType                              InetAddressType,
        	sysClusterFloatMgmtIp                                  InetAddress,
        	sysClusterFloatMgmtNetmaskType                         InetAddressType,
        	sysClusterFloatMgmtNetmask                             InetAddress,
        	sysClusterMinUpMbrs                                    Integer32,
        	sysClusterMinUpMbrsEnable                              INTEGER,
        	sysClusterMinUpMbrsAction                              INTEGER,
        	sysClusterAvailabilityState                            INTEGER,
        	sysClusterEnabledStat                                  INTEGER,
        	sysClusterDisabledParentType                           Integer32,
        	sysClusterStatusReason                                 LongDisplayString,
        	sysClusterHaState                                      INTEGER,
        	sysClusterPriSlotId                                    INTEGER,
        	sysClusterLastPriSlotId                                INTEGER,
        	sysClusterPriSelTime                                   Counter64
	}

sysClusterName OBJECT-TYPE 
	SYNTAX LongDisplayString
	MAX-ACCESS read-only
	STATUS current
	DESCRIPTION
		"The name of a cluster."
	::= { sysClusterEntry 1 } 

sysClusterEnabled OBJECT-TYPE 
	SYNTAX INTEGER {
		false(0),
		true(1)
	}
	MAX-ACCESS read-only
	STATUS current
	DESCRIPTION
		"The state indicating whether cluster environment is enabled or not."
	::= { sysClusterEntry 2 } 

sysClusterFloatMgmtIpType OBJECT-TYPE 
	SYNTAX InetAddressType
	MAX-ACCESS read-only
	STATUS current
	DESCRIPTION
		"The IP address type of the specified cluster."
	::= { sysClusterEntry 3 } 

sysClusterFloatMgmtIp OBJECT-TYPE 
	SYNTAX InetAddress
	MAX-ACCESS read-only
	STATUS current
	DESCRIPTION
		"The IP address of the specified cluster. It is interpreted within 
		 the context of a sysClusterMgmtIpType value."
	::= { sysClusterEntry 4 } 

sysClusterFloatMgmtNetmaskType OBJECT-TYPE 
	SYNTAX InetAddressType
	MAX-ACCESS read-only
	STATUS current
	DESCRIPTION
		"The netmask type of of the specified cluster IP address."
	::= { sysClusterEntry 5 } 

sysClusterFloatMgmtNetmask OBJECT-TYPE 
	SYNTAX InetAddress
	MAX-ACCESS read-only
	STATUS current
	DESCRIPTION
		"The netmask of the specified cluster IP address. It is interpreted within 
		 the context of a sysFloatMgmtNetmaskType value."
	::= { sysClusterEntry 6 } 

sysClusterMinUpMbrs OBJECT-TYPE 
	SYNTAX Integer32
	MAX-ACCESS read-only
	STATUS current
	DESCRIPTION
		"The minimum number of UP members required for the specified cluster 
		before a high availability action to be taken. 
		This is used when ltmClusterMinUpMbrsEnable is true."
	::= { sysClusterEntry 7 } 

sysClusterMinUpMbrsEnable OBJECT-TYPE 
	SYNTAX INTEGER
	MAX-ACCESS read-only
	STATUS current
	DESCRIPTION
		"The state indicating whether or not an action will be taken when the 
			minimum number of UP members requirement is not met for the specified cluster."
	::= { sysClusterEntry 8 } 

sysClusterMinUpMbrsAction OBJECT-TYPE 
	SYNTAX INTEGER {
		unusedhaaction(0),
		reboot(1),
		restart(2),
		failover(3),
		goactive(4),
		noaction(5),
		restartall(6),
		failoveraborttm(7),
		gooffline(8),
		goofflinerestart(9),
		goofflineaborttm(10),
		goofflinedownlinks(11),
		goofflinedownlinksrestart(12)
	}
	MAX-ACCESS read-only
	STATUS current
	DESCRIPTION
		"The action to be taken if the minimum number of UP members requirement 
			is not met for the specified cluster. This is used when 
			sysClusterMinUpMbrsEnable is true."
	::= { sysClusterEntry 9 } 

sysClusterAvailabilityState OBJECT-TYPE 
	SYNTAX INTEGER {
		none(0),
		green(1),
		yellow(2),
		red(3),
		blue(4)
	}
	MAX-ACCESS read-only
	STATUS current
	DESCRIPTION
		"The state of the specified cluster availability indicated in color"
	::= { sysClusterEntry 10 } 

sysClusterEnabledStat OBJECT-TYPE 
	SYNTAX INTEGER {
		none(0),
		enabled(1),
		disabled(2),
		disabledbyparent(3)
	}
	MAX-ACCESS read-only
	STATUS current
	DESCRIPTION
		"The state of the specified cluster activity status, as specified 
			by the user."
	::= { sysClusterEntry 11 } 

sysClusterDisabledParentType OBJECT-TYPE 
	SYNTAX Integer32
	MAX-ACCESS read-only
	STATUS current
	DESCRIPTION
		"The type of parent object which disabled the specified cluster."
	::= { sysClusterEntry 12 } 

sysClusterStatusReason OBJECT-TYPE 
	SYNTAX LongDisplayString
	MAX-ACCESS read-only
	STATUS current
	DESCRIPTION
		"The detail description of the cluster's status of parent object 
			which disabled the specified cluster."
	::= { sysClusterEntry 13 } 

sysClusterHaState OBJECT-TYPE 
	SYNTAX INTEGER {
		offline(0),
		forcedoffline(1),
		standby(2),
		active(3),
		unknown(4)
	}
	MAX-ACCESS read-only
	STATUS current
	DESCRIPTION
		"The state of high availability action."
	::= { sysClusterEntry 14 } 

sysClusterPriSlotId OBJECT-TYPE 
	SYNTAX INTEGER
	MAX-ACCESS read-only
	STATUS current
	DESCRIPTION
		"The slot ID of current primary slot in the specified cluster."
	::= { sysClusterEntry 15 } 

sysClusterLastPriSlotId OBJECT-TYPE 
	SYNTAX INTEGER
	MAX-ACCESS read-only
	STATUS current
	DESCRIPTION
		"The slot ID of last primary slot in the specified cluster."
	::= { sysClusterEntry 16 } 

sysClusterPriSelTime OBJECT-TYPE 
	SYNTAX Counter64
	MAX-ACCESS read-only
	STATUS current
	DESCRIPTION
		"The time interval since the primary slot is selected in the cluster."
	::= { sysClusterEntry 17 } 

--==================================================================
-- Cluster_mbr
--==================================================================
sysClusterMbrNumber OBJECT-TYPE 
	SYNTAX INTEGER
	MAX-ACCESS read-only
	STATUS current
	DESCRIPTION
		"The number of sysClusterMbr entries in the table."
	::= { sysClusterMbr 1 } 

sysClusterMbrTable OBJECT-TYPE
	SYNTAX SEQUENCE OF SysClusterMbrEntry
	MAX-ACCESS not-accessible
	STATUS current
	DESCRIPTION
		"A table containing cluster members information of the system."
	::= { sysClusterMbr 2 } 

sysClusterMbrEntry OBJECT-TYPE
	SYNTAX  SysClusterMbrEntry
	MAX-ACCESS not-accessible
	STATUS current
	DESCRIPTION
		"Columns in the sysClusterMbr Table"
	INDEX {
		sysClusterMbrCluster,
		sysClusterMbrSlotId
	}
	::= { sysClusterMbrTable 1 } 

SysClusterMbrEntry ::= 
	SEQUENCE {
        	sysClusterMbrCluster                                   LongDisplayString,
        	sysClusterMbrSlotId                                    INTEGER,
        	sysClusterMbrAvailabilityState                         INTEGER,
        	sysClusterMbrEnabledStat                               INTEGER,
        	sysClusterMbrDisabledParentType                        Integer32,
        	sysClusterMbrStatusReason                              LongDisplayString,
        	sysClusterMbrLicensed                                  INTEGER,
        	sysClusterMbrState                                     INTEGER,
        	sysClusterMbrEnabled                                   INTEGER,
        	sysClusterMbrPriming                                   INTEGER,
        	sysClusterMbrMgmtAddrType                              InetAddressType,
        	sysClusterMbrMgmtAddr                                  InetAddress,
        	sysClusterMbrHaState                                   INTEGER
	}

sysClusterMbrCluster OBJECT-TYPE 
	SYNTAX LongDisplayString
	MAX-ACCESS read-only
	STATUS current
	DESCRIPTION
		"The name of a cluster."
	::= { sysClusterMbrEntry 1 } 

sysClusterMbrSlotId OBJECT-TYPE 
	SYNTAX INTEGER(1..2147483647)
	MAX-ACCESS read-only
	STATUS current
	DESCRIPTION
		"The slot id in the specified cluster."
	::= { sysClusterMbrEntry 2 } 

sysClusterMbrAvailabilityState OBJECT-TYPE 
	SYNTAX INTEGER {
		none(0),
		green(1),
		yellow(2),
		red(3),
		blue(4)
	}
	MAX-ACCESS read-only
	STATUS current
	DESCRIPTION
		"The state of the specified cluster member availability indicated in color"
	::= { sysClusterMbrEntry 3 } 

sysClusterMbrEnabledStat OBJECT-TYPE 
	SYNTAX INTEGER {
		none(0),
		enabled(1),
		disabled(2),
		disabledbyparent(3)
	}
	MAX-ACCESS read-only
	STATUS current
	DESCRIPTION
		"The state of the specified cluster member activity status, as specified 
			by the user."
	::= { sysClusterMbrEntry 4 } 

sysClusterMbrDisabledParentType OBJECT-TYPE 
	SYNTAX Integer32
	MAX-ACCESS read-only
	STATUS current
	DESCRIPTION
		"The type of parent object which disabled the specified cluster member."
	::= { sysClusterMbrEntry 5 } 

sysClusterMbrStatusReason OBJECT-TYPE 
	SYNTAX LongDisplayString
	MAX-ACCESS read-only
	STATUS current
	DESCRIPTION
		"The detail description of the cluster's status of parent object 
			which disabled the specified cluster member."
	::= { sysClusterMbrEntry 6 } 

sysClusterMbrLicensed OBJECT-TYPE 
	SYNTAX INTEGER {
		false(0),
		true(1)
	}
	MAX-ACCESS read-only
	STATUS current
	DESCRIPTION
		"The state indicating whether or not the specified cluster member is licensed."
	::= { sysClusterMbrEntry 7 } 

sysClusterMbrState OBJECT-TYPE 
	SYNTAX INTEGER {
		initial(0),
		quorumwait(1),
		quorum(2),
		running(3),
		shutdown(4)
	}
	MAX-ACCESS read-only
	STATUS current
	DESCRIPTION
		"The state which the specified cluster member in at."
	::= { sysClusterMbrEntry 8 } 

sysClusterMbrEnabled OBJECT-TYPE 
	SYNTAX INTEGER {
		false(0),
		true(1)
	}
	MAX-ACCESS read-only
	STATUS current
	DESCRIPTION
		"The state indicating whehter the specified member is enabled or not."
	::= { sysClusterMbrEntry 9 } 

sysClusterMbrPriming OBJECT-TYPE 
	SYNTAX INTEGER {
		false(0),
		true(1)
	}
	MAX-ACCESS read-only
	STATUS current
	DESCRIPTION
		"The state indicating whether or not priming is enabled."
	::= { sysClusterMbrEntry 10 } 

sysClusterMbrMgmtAddrType OBJECT-TYPE 
	SYNTAX InetAddressType
	MAX-ACCESS read-only
	STATUS current
	DESCRIPTION
		"The IP address type of the specified cluster member."
	::= { sysClusterMbrEntry 11 } 

sysClusterMbrMgmtAddr OBJECT-TYPE 
	SYNTAX InetAddress
	MAX-ACCESS read-only
	STATUS current
	DESCRIPTION
		"The IP address of the specified cluster member. It is interpreted within 
		 the context of a sysClusterMbrMgmtAddrType value."
	::= { sysClusterMbrEntry 12 } 

sysClusterMbrHaState OBJECT-TYPE 
	SYNTAX INTEGER {
		unknown(0),
		offline(1),
		forcedoffline(2),
		standby(3),
		active(4)
	}
	MAX-ACCESS read-only
	STATUS current
	DESCRIPTION
		"The state of high availability action of the specified cluster member."
	::= { sysClusterMbrEntry 13 } 

--==================================================================
-- Software_volume
--==================================================================
sysSwVolumeNumber OBJECT-TYPE 
	SYNTAX INTEGER
	MAX-ACCESS read-only
	STATUS current
	DESCRIPTION
		"The number of sysSoftwareVolume entries in the table."
	::= { sysSoftwareVolume 1 } 

sysSwVolumeTable OBJECT-TYPE
	SYNTAX SEQUENCE OF SysSwVolumeEntry
	MAX-ACCESS not-accessible
	STATUS current
	DESCRIPTION
		"A table containing software volume information on the system."
	::= { sysSoftwareVolume 2 } 

sysSwVolumeEntry OBJECT-TYPE
	SYNTAX  SysSwVolumeEntry
	MAX-ACCESS not-accessible
	STATUS current
	DESCRIPTION
		"Columns in the sysSwVolume Table"
	INDEX {
		sysSwVolumeSlotId,
		sysSwVolumeName
	}
	::= { sysSwVolumeTable 1 } 

SysSwVolumeEntry ::= 
	SEQUENCE {
        	sysSwVolumeSlotId                                      INTEGER,
        	sysSwVolumeName                                        LongDisplayString,
        	sysSwVolumeSize                                        LongDisplayString,
        	sysSwVolumeActive                                      INTEGER
	}

sysSwVolumeSlotId OBJECT-TYPE 
	SYNTAX INTEGER(1..2147483647)
	MAX-ACCESS read-only
	STATUS current
	DESCRIPTION
		"The slot ID."
	::= { sysSwVolumeEntry 1 } 

sysSwVolumeName OBJECT-TYPE 
	SYNTAX LongDisplayString
	MAX-ACCESS read-only
	STATUS current
	DESCRIPTION
		"The harddisk name."
	::= { sysSwVolumeEntry 2 } 

sysSwVolumeSize OBJECT-TYPE 
	SYNTAX LongDisplayString
	MAX-ACCESS read-only
	STATUS current
	DESCRIPTION
		"The space of the specified harddisk."
	::= { sysSwVolumeEntry 3 } 

sysSwVolumeActive OBJECT-TYPE 
	SYNTAX INTEGER {
		false(0),
		true(1)
	}
	MAX-ACCESS read-only
	STATUS current
	DESCRIPTION
		"The state indicating whether or not the specified slot is active."
	::= { sysSwVolumeEntry 4 } 

--==================================================================
-- Software_image
--==================================================================
sysSwImageNumber OBJECT-TYPE 
	SYNTAX INTEGER
	MAX-ACCESS read-only
	STATUS current
	DESCRIPTION
		"The number of sysSoftwareImage entries in the table."
	::= { sysSoftwareImage 1 } 

sysSwImageTable OBJECT-TYPE
	SYNTAX SEQUENCE OF SysSwImageEntry
	MAX-ACCESS not-accessible
	STATUS current
	DESCRIPTION
		"A table containing software image information on the system."
	::= { sysSoftwareImage 2 } 

sysSwImageEntry OBJECT-TYPE
	SYNTAX  SysSwImageEntry
	MAX-ACCESS not-accessible
	STATUS current
	DESCRIPTION
		"Columns in the sysSwImage Table"
	INDEX {
		sysSwImageSlotId,
		sysSwImageFilename
	}
	::= { sysSwImageTable 1 } 

SysSwImageEntry ::= 
	SEQUENCE {
        	sysSwImageSlotId                                       INTEGER,
        	sysSwImageFilename                                     LongDisplayString,
        	sysSwImageProduct                                      LongDisplayString,
        	sysSwImageVersion                                      LongDisplayString,
        	sysSwImageBuild                                        LongDisplayString,
        	sysSwImageChksum                                       LongDisplayString,
        	sysSwImageVerified                                     INTEGER,
        	sysSwImageBuildDate                                    LongDisplayString,
        	sysSwImageLastModified                                 LongDisplayString,
        	sysSwImageFileSize                                     LongDisplayString
	}

sysSwImageSlotId OBJECT-TYPE 
	SYNTAX INTEGER(1..2147483647)
	MAX-ACCESS read-only
	STATUS current
	DESCRIPTION
		"The slot ID."
	::= { sysSwImageEntry 1 } 

sysSwImageFilename OBJECT-TYPE 
	SYNTAX LongDisplayString
	MAX-ACCESS read-only
	STATUS current
	DESCRIPTION
		"The software image name."
	::= { sysSwImageEntry 2 } 

sysSwImageProduct OBJECT-TYPE 
	SYNTAX LongDisplayString
	MAX-ACCESS read-only
	STATUS current
	DESCRIPTION
		"The product name of the specified image."
	::= { sysSwImageEntry 3 } 

sysSwImageVersion OBJECT-TYPE 
	SYNTAX LongDisplayString
	MAX-ACCESS read-only
	STATUS current
	DESCRIPTION
		"The version of the specified image."
	::= { sysSwImageEntry 4 } 

sysSwImageBuild OBJECT-TYPE 
	SYNTAX LongDisplayString
	MAX-ACCESS read-only
	STATUS current
	DESCRIPTION
		"The build number of the specified image."
	::= { sysSwImageEntry 5 } 

sysSwImageChksum OBJECT-TYPE 
	SYNTAX LongDisplayString
	MAX-ACCESS read-only
	STATUS current
	DESCRIPTION
		"The chksum of specified image."
	::= { sysSwImageEntry 6 } 

sysSwImageVerified OBJECT-TYPE 
	SYNTAX INTEGER {
		false(0),
		true(1)
	}
	MAX-ACCESS read-only
	STATUS current
	DESCRIPTION
		"The state indicating whether the specified image is verified or not."
	::= { sysSwImageEntry 7 } 

sysSwImageBuildDate OBJECT-TYPE 
	SYNTAX LongDisplayString
	MAX-ACCESS read-only
	STATUS current
	DESCRIPTION
		"The date when the specified image is built."
	::= { sysSwImageEntry 8 } 

sysSwImageLastModified OBJECT-TYPE 
	SYNTAX LongDisplayString
	MAX-ACCESS read-only
	STATUS current
	DESCRIPTION
		"The date when the specified image is last modified."
	::= { sysSwImageEntry 9 } 

sysSwImageFileSize OBJECT-TYPE 
	SYNTAX LongDisplayString
	MAX-ACCESS read-only
	STATUS current
	DESCRIPTION
		"The size of the specified software image."
	::= { sysSwImageEntry 10 } 

--==================================================================
-- Software_hotfix
--==================================================================
sysSwHotfixNumber OBJECT-TYPE 
	SYNTAX INTEGER
	MAX-ACCESS read-only
	STATUS current
	DESCRIPTION
		"The number of sysSoftwareHotfix entries in the table."
	::= { sysSoftwareHotfix 1 } 

sysSwHotfixTable OBJECT-TYPE
	SYNTAX SEQUENCE OF SysSwHotfixEntry
	MAX-ACCESS not-accessible
	STATUS current
	DESCRIPTION
		"A table containing hotfix software information on the system."
	::= { sysSoftwareHotfix 2 } 

sysSwHotfixEntry OBJECT-TYPE
	SYNTAX  SysSwHotfixEntry
	MAX-ACCESS not-accessible
	STATUS current
	DESCRIPTION
		"Columns in the sysSwHotfix Table"
	INDEX {
		sysSwHotfixSlotId,
		sysSwHotfixFilename
	}
	::= { sysSwHotfixTable 1 } 

SysSwHotfixEntry ::= 
	SEQUENCE {
        	sysSwHotfixSlotId                                      INTEGER,
        	sysSwHotfixFilename                                    LongDisplayString,
        	sysSwHotfixProduct                                     LongDisplayString,
        	sysSwHotfixVersion                                     LongDisplayString,
        	sysSwHotfixBuild                                       LongDisplayString,
        	sysSwHotfixChksum                                      LongDisplayString,
        	sysSwHotfixVerified                                    INTEGER,
        	sysSwHotfixHotfixId                                    LongDisplayString,
        	sysSwHotfixHotfixTitle                                 LongDisplayString
	}

sysSwHotfixSlotId OBJECT-TYPE 
	SYNTAX INTEGER(1..2147483647)
	MAX-ACCESS read-only
	STATUS current
	DESCRIPTION
		"The slot ID."
	::= { sysSwHotfixEntry 1 } 

sysSwHotfixFilename OBJECT-TYPE 
	SYNTAX LongDisplayString
	MAX-ACCESS read-only
	STATUS current
	DESCRIPTION
		"The software image name."
	::= { sysSwHotfixEntry 2 } 

sysSwHotfixProduct OBJECT-TYPE 
	SYNTAX LongDisplayString
	MAX-ACCESS read-only
	STATUS current
	DESCRIPTION
		"The product name of the specified hotfix image."
	::= { sysSwHotfixEntry 3 } 

sysSwHotfixVersion OBJECT-TYPE 
	SYNTAX LongDisplayString
	MAX-ACCESS read-only
	STATUS current
	DESCRIPTION
		"The version of the specified hotfix image."
	::= { sysSwHotfixEntry 4 } 

sysSwHotfixBuild OBJECT-TYPE 
	SYNTAX LongDisplayString
	MAX-ACCESS read-only
	STATUS current
	DESCRIPTION
		"The build number of the specified hotfix image."
	::= { sysSwHotfixEntry 5 } 

sysSwHotfixChksum OBJECT-TYPE 
	SYNTAX LongDisplayString
	MAX-ACCESS read-only
	STATUS current
	DESCRIPTION
		"The chksum of specified hotfix image."
	::= { sysSwHotfixEntry 6 } 

sysSwHotfixVerified OBJECT-TYPE 
	SYNTAX INTEGER {
		false(0),
		true(1)
	}
	MAX-ACCESS read-only
	STATUS current
	DESCRIPTION
		"The state indicating whether the specified hotfix image is verified or not."
	::= { sysSwHotfixEntry 7 } 

sysSwHotfixHotfixId OBJECT-TYPE 
	SYNTAX LongDisplayString
	MAX-ACCESS read-only
	STATUS current
	DESCRIPTION
		"The ID of the hotfix image."
	::= { sysSwHotfixEntry 8 } 

sysSwHotfixHotfixTitle OBJECT-TYPE 
	SYNTAX LongDisplayString
	MAX-ACCESS read-only
	STATUS current
	DESCRIPTION
		"The title of the hotfix image."
	::= { sysSwHotfixEntry 9 } 

--==================================================================
-- Software_status
--==================================================================
sysSwStatusNumber OBJECT-TYPE 
	SYNTAX INTEGER
	MAX-ACCESS read-only
	STATUS current
	DESCRIPTION
		"The number of sysSoftwareStatus entries in the table."
	::= { sysSoftwareStatus 1 } 

sysSwStatusTable OBJECT-TYPE
	SYNTAX SEQUENCE OF SysSwStatusEntry
	MAX-ACCESS not-accessible
	STATUS current
	DESCRIPTION
		"A table containing software status information on the system."
	::= { sysSoftwareStatus 2 } 

sysSwStatusEntry OBJECT-TYPE
	SYNTAX  SysSwStatusEntry
	MAX-ACCESS not-accessible
	STATUS current
	DESCRIPTION
		"Columns in the sysSwStatus Table"
	INDEX {
		sysSwStatusSlotId,
		sysSwStatusVolume
	}
	::= { sysSwStatusTable 1 } 

SysSwStatusEntry ::= 
	SEQUENCE {
        	sysSwStatusSlotId                                      INTEGER,
        	sysSwStatusVolume                                      LongDisplayString,
        	sysSwStatusProduct                                     LongDisplayString,
        	sysSwStatusVersion                                     LongDisplayString,
        	sysSwStatusBuild                                       LongDisplayString,
        	sysSwStatusActive                                      INTEGER
	}

sysSwStatusSlotId OBJECT-TYPE 
	SYNTAX INTEGER(1..2147483647)
	MAX-ACCESS read-only
	STATUS current
	DESCRIPTION
		"The slot ID."
	::= { sysSwStatusEntry 1 } 

sysSwStatusVolume OBJECT-TYPE 
	SYNTAX LongDisplayString
	MAX-ACCESS read-only
	STATUS current
	DESCRIPTION
		"The harddisk name."
	::= { sysSwStatusEntry 2 } 

sysSwStatusProduct OBJECT-TYPE 
	SYNTAX LongDisplayString
	MAX-ACCESS read-only
	STATUS current
	DESCRIPTION
		"The product name of the specified software."
	::= { sysSwStatusEntry 3 } 

sysSwStatusVersion OBJECT-TYPE 
	SYNTAX LongDisplayString
	MAX-ACCESS read-only
	STATUS current
	DESCRIPTION
		"The version of the specified software."
	::= { sysSwStatusEntry 4 } 

sysSwStatusBuild OBJECT-TYPE 
	SYNTAX LongDisplayString
	MAX-ACCESS read-only
	STATUS current
	DESCRIPTION
		"The build number of the specified software."
	::= { sysSwStatusEntry 5 } 

sysSwStatusActive OBJECT-TYPE 
	SYNTAX INTEGER {
		false(0),
		true(1)
	}
	MAX-ACCESS read-only
	STATUS current
	DESCRIPTION
		"The state indicating whether the system is acive or not."
	::= { sysSwStatusEntry 6 } 

--==================================================================
-- Global_host_info_stat
--==================================================================
sysGlobalHostResetStats OBJECT-TYPE 
	SYNTAX INTEGER
	MAX-ACCESS read-write
	STATUS current
	DESCRIPTION
		"The action to reset resetable statistics data in  sysGlobalHost. 
		 Setting this value to 1 will reset statistics data. 
		 Note, some statistics data may not be reset including data that are incremental counters."
	::= { sysGlobalHost 1 } 

sysGlobalHostMemTotal OBJECT-TYPE 
	SYNTAX CounterBasedGauge64
	MAX-ACCESS read-only
	STATUS current
	DESCRIPTION
		"The total host memory in bytes for the system."
	::= { sysGlobalHost 2 } 

sysGlobalHostMemUsed OBJECT-TYPE 
	SYNTAX CounterBasedGauge64
	MAX-ACCESS read-only
	STATUS current
	DESCRIPTION
		"The host memory in bytes currently in use for the system."
	::= { sysGlobalHost 3 } 

sysGlobalHostCpuCount OBJECT-TYPE 
	SYNTAX Counter64
	MAX-ACCESS read-only
	STATUS current
	DESCRIPTION
		"The number of CPUs in the system."
	::= { sysGlobalHost 4 } 

sysGlobalHostActiveCpuCount OBJECT-TYPE 
	SYNTAX Counter64
	MAX-ACCESS read-only
	STATUS current
	DESCRIPTION
		"The number of active CPUs in the system."
	::= { sysGlobalHost 5 } 

sysGlobalHostCpuUser OBJECT-TYPE 
	SYNTAX Counter64
	MAX-ACCESS read-only
	STATUS current
	DESCRIPTION
		"The time spent by the specified processor in user context for the system."
	::= { sysGlobalHost 6 } 

sysGlobalHostCpuNice OBJECT-TYPE 
	SYNTAX Counter64
	MAX-ACCESS read-only
	STATUS current
	DESCRIPTION
		"The time spent by the specified processor running niced processes for the system."
	::= { sysGlobalHost 7 } 

sysGlobalHostCpuSystem OBJECT-TYPE 
	SYNTAX Counter64
	MAX-ACCESS read-only
	STATUS current
	DESCRIPTION
		"The time spent by the specified processor servicing system calls for the system."
	::= { sysGlobalHost 8 } 

sysGlobalHostCpuIdle OBJECT-TYPE 
	SYNTAX Counter64
	MAX-ACCESS read-only
	STATUS current
	DESCRIPTION
		"The time spent by the specified processor doing nothing for the system."
	::= { sysGlobalHost 9 } 

sysGlobalHostCpuIrq OBJECT-TYPE 
	SYNTAX Counter64
	MAX-ACCESS read-only
	STATUS current
	DESCRIPTION
		"The time spent by the specified processor servicing hardware interrupts for the system."
	::= { sysGlobalHost 10 } 

sysGlobalHostCpuSoftirq OBJECT-TYPE 
	SYNTAX Counter64
	MAX-ACCESS read-only
	STATUS current
	DESCRIPTION
		"The time spent by the specified processor servicing soft interrupts for the system."
	::= { sysGlobalHost 11 } 

sysGlobalHostCpuIowait OBJECT-TYPE 
	SYNTAX Counter64
	MAX-ACCESS read-only
	STATUS current
	DESCRIPTION
		"The time spent by the specified processor waiting for external I/O to complete for the system."
	::= { sysGlobalHost 12 } 

sysGlobalHostCpuUsageRatio OBJECT-TYPE 
	SYNTAX CounterBasedGauge64
	MAX-ACCESS read-only
	STATUS current
	DESCRIPTION
		"This is usage ratio of CPU for the system. It is calculated by 
		(sum of deltas for user, niced, system)/(sum of deltas of user, niced, system, idle, irq, softirq, and iowait),
		where each delta is the difference for each stat over the last 10-second interval;
		user: sysGlobalHostCpuUser;
		niced: sysGlobalHostCpuNiced;
			stolen: sysGlobalHostCpuStolen;
		system: sysGlobalHostCpuSystem;
		idle: sysGlobalHostCpuIdle;
		irq: sysGlobalHostCpuIrq;
		iowait: sysGlobalHostCpuIowait"
	::= { sysGlobalHost 13 } 

sysGlobalHostCpuUser5s OBJECT-TYPE 
	SYNTAX CounterBasedGauge64
	MAX-ACCESS read-only
	STATUS current
	DESCRIPTION
		"The average time spent by the specified processor in user context for the system in the last five seconds."
	::= { sysGlobalHost 14 } 

sysGlobalHostCpuNice5s OBJECT-TYPE 
	SYNTAX CounterBasedGauge64
	MAX-ACCESS read-only
	STATUS current
	DESCRIPTION
		"The average time spent by the specified processor running niced processes for the system in the last five seconds."
	::= { sysGlobalHost 15 } 

sysGlobalHostCpuSystem5s OBJECT-TYPE 
	SYNTAX CounterBasedGauge64
	MAX-ACCESS read-only
	STATUS current
	DESCRIPTION
		"The average time spent by the specified processor servicing system calls for the system in the last five seconds."
	::= { sysGlobalHost 16 } 

sysGlobalHostCpuIdle5s OBJECT-TYPE 
	SYNTAX CounterBasedGauge64
	MAX-ACCESS read-only
	STATUS current
	DESCRIPTION
		"The average time spent by the specified processor doing nothing for the system in the last five seconds."
	::= { sysGlobalHost 17 } 

sysGlobalHostCpuIrq5s OBJECT-TYPE 
	SYNTAX CounterBasedGauge64
	MAX-ACCESS read-only
	STATUS current
	DESCRIPTION
		"The average time spent by the specified processor servicing hardware interrupts for the system in the last five seconds."
	::= { sysGlobalHost 18 } 

sysGlobalHostCpuSoftirq5s OBJECT-TYPE 
	SYNTAX CounterBasedGauge64
	MAX-ACCESS read-only
	STATUS current
	DESCRIPTION
		"The average time spent by the specified processor servicing soft interrupts for the system in the last five seconds."
	::= { sysGlobalHost 19 } 

sysGlobalHostCpuIowait5s OBJECT-TYPE 
	SYNTAX CounterBasedGauge64
	MAX-ACCESS read-only
	STATUS current
	DESCRIPTION
		"The average time spent by the specified processor waiting for external I/O to complete for the system in the last five seconds."
	::= { sysGlobalHost 20 } 

sysGlobalHostCpuUsageRatio5s OBJECT-TYPE 
	SYNTAX CounterBasedGauge64
	MAX-ACCESS read-only
	STATUS current
	DESCRIPTION
		"This is  average usage ratio of CPU for the system in the last five seconds. It is calculated by 
		(sum of deltas for user, niced, system)/(sum of deltas of user, niced, system, idle, irq, softirq, and iowait),
		where each delta is the difference for each stat over the last 5-second interval;
		user: sysGlobalHostCpuUser5s;
		niced: sysGlobalHostCpuNiced5s;
			stolen: sysGlobalHostCpuStolen5s;
		system: sysGlobalHostCpuSystem5s;
		idle: sysGlobalHostCpuIdle5s;
		irq: sysGlobalHostCpuIrq5s;
		iowait: sysGlobalHostCpuIowait5s"
	::= { sysGlobalHost 21 } 

sysGlobalHostCpuUser1m OBJECT-TYPE 
	SYNTAX CounterBasedGauge64
	MAX-ACCESS read-only
	STATUS current
	DESCRIPTION
		"The average time spent by the specified processor in user context for the system in the last one minute."
	::= { sysGlobalHost 22 } 

sysGlobalHostCpuNice1m OBJECT-TYPE 
	SYNTAX CounterBasedGauge64
	MAX-ACCESS read-only
	STATUS current
	DESCRIPTION
		"The average time spent by the specified processor running niced processes for the system in the last one minute."
	::= { sysGlobalHost 23 } 

sysGlobalHostCpuSystem1m OBJECT-TYPE 
	SYNTAX CounterBasedGauge64
	MAX-ACCESS read-only
	STATUS current
	DESCRIPTION
		"The average time spent by the specified processor servicing system calls for the system in the last one minute."
	::= { sysGlobalHost 24 } 

sysGlobalHostCpuIdle1m OBJECT-TYPE 
	SYNTAX CounterBasedGauge64
	MAX-ACCESS read-only
	STATUS current
	DESCRIPTION
		"The average time spent by the specified processor doing nothing for the system in the last one minute."
	::= { sysGlobalHost 25 } 

sysGlobalHostCpuIrq1m OBJECT-TYPE 
	SYNTAX CounterBasedGauge64
	MAX-ACCESS read-only
	STATUS current
	DESCRIPTION
		"The average time spent by the specified processor servicing hardware interrupts for the system in the last one minute."
	::= { sysGlobalHost 26 } 

sysGlobalHostCpuSoftirq1m OBJECT-TYPE 
	SYNTAX CounterBasedGauge64
	MAX-ACCESS read-only
	STATUS current
	DESCRIPTION
		"The average time spent by the specified processor servicing soft interrupts for the system in the last one minute."
	::= { sysGlobalHost 27 } 

sysGlobalHostCpuIowait1m OBJECT-TYPE 
	SYNTAX CounterBasedGauge64
	MAX-ACCESS read-only
	STATUS current
	DESCRIPTION
		"The average time spent by the specified processor waiting for external I/O to complete for the system in the last one minute."
	::= { sysGlobalHost 28 } 

sysGlobalHostCpuUsageRatio1m OBJECT-TYPE 
	SYNTAX CounterBasedGauge64
	MAX-ACCESS read-only
	STATUS current
	DESCRIPTION
		"This is  average usage ratio of CPU for the system in the last one minute. It is calculated by 
		(sum of deltas for user, niced, system)/(sum of deltas of user, niced, system, idle, irq, softirq, and iowait),
		where each delta is the difference for each stat over the last 1-minute interval;
		user: sysGlobalHostCpuUser1m;
		niced: sysGlobalHostCpuNiced1m;
			stolen: sysGlobalHostCpuStolen1m;
		system: sysGlobalHostCpuSystem1m;
		idle: sysGlobalHostCpuIdle1m;
		irq: sysGlobalHostCpuIrq1m;
		iowait: sysGlobalHostCpuIowait1m"
	::= { sysGlobalHost 29 } 

sysGlobalHostCpuUser5m OBJECT-TYPE 
	SYNTAX CounterBasedGauge64
	MAX-ACCESS read-only
	STATUS current
	DESCRIPTION
		"The average time spent by the specified processor in user context for the system in the last five minutes."
	::= { sysGlobalHost 30 } 

sysGlobalHostCpuNice5m OBJECT-TYPE 
	SYNTAX CounterBasedGauge64
	MAX-ACCESS read-only
	STATUS current
	DESCRIPTION
		"The average time spent by the specified processor running niced processes for the system in the last five minutes."
	::= { sysGlobalHost 31 } 

sysGlobalHostCpuSystem5m OBJECT-TYPE 
	SYNTAX CounterBasedGauge64
	MAX-ACCESS read-only
	STATUS current
	DESCRIPTION
		"The average time spent by the specified processor servicing system calls for the system in the last five minutes."
	::= { sysGlobalHost 32 } 

sysGlobalHostCpuIdle5m OBJECT-TYPE 
	SYNTAX CounterBasedGauge64
	MAX-ACCESS read-only
	STATUS current
	DESCRIPTION
		"The average time spent by the specified processor doing nothing for the system in the last five minutes."
	::= { sysGlobalHost 33 } 

sysGlobalHostCpuIrq5m OBJECT-TYPE 
	SYNTAX CounterBasedGauge64
	MAX-ACCESS read-only
	STATUS current
	DESCRIPTION
		"The average time spent by the specified processor servicing hardware interrupts for the system in the last five minutes."
	::= { sysGlobalHost 34 } 

sysGlobalHostCpuSoftirq5m OBJECT-TYPE 
	SYNTAX CounterBasedGauge64
	MAX-ACCESS read-only
	STATUS current
	DESCRIPTION
		"The average time spent by the specified processor servicing soft interrupts for the system in the last five minutes."
	::= { sysGlobalHost 35 } 

sysGlobalHostCpuIowait5m OBJECT-TYPE 
	SYNTAX CounterBasedGauge64
	MAX-ACCESS read-only
	STATUS current
	DESCRIPTION
		"The average time spent by the specified processor waiting for external I/O to complete for the system in the last five minutes."
	::= { sysGlobalHost 36 } 

sysGlobalHostCpuUsageRatio5m OBJECT-TYPE 
	SYNTAX CounterBasedGauge64
	MAX-ACCESS read-only
	STATUS current
	DESCRIPTION
		"This is  average usage ratio of CPU for the system in the last five minutes. It is calculated by 
		(sum of deltas for user, niced, system)/(sum of deltas of user, niced, system, idle, irq, softirq, and iowait),
		where each delta is the difference for each stat over the last 5-minute interval;
		user: sysGlobalHostCpuUser5m;
		niced: sysGlobalHostCpuNiced5m;
			stolen: sysGlobalHostCpuStolen5m;
		system: sysGlobalHostCpuSystem5m;
		idle: sysGlobalHostCpuIdle5m;
		irq: sysGlobalHostCpuIrq5m;
		iowait: sysGlobalHostCpuIowait5m"
	::= { sysGlobalHost 37 } 

sysGlobalHostCpuStolen OBJECT-TYPE 
	SYNTAX CounterBasedGauge64
	MAX-ACCESS read-only
	STATUS current
	DESCRIPTION
		"The time 'stolen' from the system (for virtual machines)."
	::= { sysGlobalHost 38 } 

sysGlobalHostCpuStolen5s OBJECT-TYPE 
	SYNTAX CounterBasedGauge64
	MAX-ACCESS read-only
	STATUS current
	DESCRIPTION
		"The average time 'stolen' from the system in the last five seconds."
	::= { sysGlobalHost 39 } 

sysGlobalHostCpuStolen1m OBJECT-TYPE 
	SYNTAX CounterBasedGauge64
	MAX-ACCESS read-only
	STATUS current
	DESCRIPTION
		"The average time 'stolen' from the system in the last one minute."
	::= { sysGlobalHost 40 } 

sysGlobalHostCpuStolen5m OBJECT-TYPE 
	SYNTAX CounterBasedGauge64
	MAX-ACCESS read-only
	STATUS current
	DESCRIPTION
		"The average time 'stolen' from the system in the last five minutes."
	::= { sysGlobalHost 41 } 

sysGlobalHostMemTotalKb OBJECT-TYPE 
	SYNTAX CounterBasedGauge64
	MAX-ACCESS read-only
	STATUS current
	DESCRIPTION
		"The total host memory in Kilobytes for the system."
	::= { sysGlobalHost 42 } 

sysGlobalHostMemUsedKb OBJECT-TYPE 
	SYNTAX CounterBasedGauge64
	MAX-ACCESS read-only
	STATUS current
	DESCRIPTION
		"The host memory in Kilobytes currently in use for the system."
	::= { sysGlobalHost 43 } 

--==================================================================
-- Module_allocation
--==================================================================
sysModuleAllocationNumber OBJECT-TYPE 
	SYNTAX INTEGER
	MAX-ACCESS read-only
	STATUS current
	DESCRIPTION
		"The number of sysModuleAllocation entries in the table."
	::= { sysModuleAllocation 1 } 

sysModuleAllocationTable OBJECT-TYPE
	SYNTAX SEQUENCE OF SysModuleAllocationEntry
	MAX-ACCESS not-accessible
	STATUS current
	DESCRIPTION
		"Resource allocation information about modules on the system"
	::= { sysModuleAllocation 2 } 

sysModuleAllocationEntry OBJECT-TYPE
	SYNTAX  SysModuleAllocationEntry
	MAX-ACCESS not-accessible
	STATUS current
	DESCRIPTION
		"Columns in the sysModuleAllocation Table"
	INDEX {
		sysModuleAllocationName
	}
	::= { sysModuleAllocationTable 1 } 

SysModuleAllocationEntry ::= 
	SEQUENCE {
        	sysModuleAllocationName                                LongDisplayString,
        	sysModuleAllocationProvisionLevel                      INTEGER,
        	sysModuleAllocationMemoryRatio                         INTEGER,
        	sysModuleAllocationCpuRatio                            INTEGER,
        	sysModuleAllocationDiskRatio                           INTEGER
	}

sysModuleAllocationName OBJECT-TYPE 
	SYNTAX LongDisplayString
	MAX-ACCESS read-only
	STATUS current
	DESCRIPTION
		"The name of the Module"
	::= { sysModuleAllocationEntry 1 } 

sysModuleAllocationProvisionLevel OBJECT-TYPE 
	SYNTAX INTEGER {
		none(1),
		minimum(2),
		nominal(3),
		dedicated(4),
		custom(5)
	}
	MAX-ACCESS read-only
	STATUS current
	DESCRIPTION
		"The provisioning level indicates how the systems resources
		are distributed amongst the modules"
	::= { sysModuleAllocationEntry 2 } 

sysModuleAllocationMemoryRatio OBJECT-TYPE 
	SYNTAX INTEGER
	MAX-ACCESS read-only
	STATUS current
	DESCRIPTION
		"The ratio of available memory to allocate. Only valid if level is 'custom'"
	::= { sysModuleAllocationEntry 3 } 

sysModuleAllocationCpuRatio OBJECT-TYPE 
	SYNTAX INTEGER
	MAX-ACCESS read-only
	STATUS current
	DESCRIPTION
		"The ratio of CPU to allocate to this module. Only valid if level is 'custom'"
	::= { sysModuleAllocationEntry 4 } 

sysModuleAllocationDiskRatio OBJECT-TYPE 
	SYNTAX INTEGER
	MAX-ACCESS read-only
	STATUS current
	DESCRIPTION
		"The ratio of available disk space to allocate to this module. Only valid if level is 'custom'"
	::= { sysModuleAllocationEntry 5 } 

--==================================================================
-- Global_tmm_stat
--==================================================================
sysGlobalTmmStatResetStats OBJECT-TYPE 
	SYNTAX INTEGER
	MAX-ACCESS read-write
	STATUS current
	DESCRIPTION
		"The action to reset resetable statistics data in  sysGlobalTmmStat. 
		 Setting this value to 1 will reset statistics data. 
		 Note, some statistics data may not be reset including data that are incremental counters."
	::= { sysGlobalTmmStat 1 } 

sysGlobalTmmStatNpus OBJECT-TYPE 
	SYNTAX Counter64
	MAX-ACCESS read-only
	STATUS current
	DESCRIPTION
		"The number of TMMs (Traffic Management Module) on the system."
	::= { sysGlobalTmmStat 2 } 

sysGlobalTmmStatClientPktsIn OBJECT-TYPE 
	SYNTAX Counter64
	MAX-ACCESS read-only
	STATUS current
	DESCRIPTION
		"The number of packets received by the system from client-side."
	::= { sysGlobalTmmStat 3 } 

sysGlobalTmmStatClientBytesIn OBJECT-TYPE 
	SYNTAX Counter64
	MAX-ACCESS read-only
	STATUS current
	DESCRIPTION
		"The number of bytes received by the system from client-side."
	::= { sysGlobalTmmStat 4 } 

sysGlobalTmmStatClientPktsOut OBJECT-TYPE 
	SYNTAX Counter64
	MAX-ACCESS read-only
	STATUS current
	DESCRIPTION
		"The number of packets sent to client-side from the system."
	::= { sysGlobalTmmStat 5 } 

sysGlobalTmmStatClientBytesOut OBJECT-TYPE 
	SYNTAX Counter64
	MAX-ACCESS read-only
	STATUS current
	DESCRIPTION
		"The number of bytes sent to client-side from the system."
	::= { sysGlobalTmmStat 6 } 

sysGlobalTmmStatClientMaxConns OBJECT-TYPE 
	SYNTAX Counter64
	MAX-ACCESS read-only
	STATUS current
	DESCRIPTION
		"The maximum connections from client-side to the system."
	::= { sysGlobalTmmStat 7 } 

sysGlobalTmmStatClientTotConns OBJECT-TYPE 
	SYNTAX Counter64
	MAX-ACCESS read-only
	STATUS current
	DESCRIPTION
		"The total connections from client-side to the system."
	::= { sysGlobalTmmStat 8 } 

sysGlobalTmmStatClientCurConns OBJECT-TYPE 
	SYNTAX CounterBasedGauge64
	MAX-ACCESS read-only
	STATUS current
	DESCRIPTION
		"The current connections from client-side to the system."
	::= { sysGlobalTmmStat 9 } 

sysGlobalTmmStatServerPktsIn OBJECT-TYPE 
	SYNTAX Counter64
	MAX-ACCESS read-only
	STATUS current
	DESCRIPTION
		"The number of packets received by the system from server-side."
	::= { sysGlobalTmmStat 10 } 

sysGlobalTmmStatServerBytesIn OBJECT-TYPE 
	SYNTAX Counter64
	MAX-ACCESS read-only
	STATUS current
	DESCRIPTION
		"The number of bytes received by the system from server-side."
	::= { sysGlobalTmmStat 11 } 

sysGlobalTmmStatServerPktsOut OBJECT-TYPE 
	SYNTAX Counter64
	MAX-ACCESS read-only
	STATUS current
	DESCRIPTION
		"The number of packets sent to server-side from the system."
	::= { sysGlobalTmmStat 12 } 

sysGlobalTmmStatServerBytesOut OBJECT-TYPE 
	SYNTAX Counter64
	MAX-ACCESS read-only
	STATUS current
	DESCRIPTION
		"The number of bytes sent to server-side from the system."
	::= { sysGlobalTmmStat 13 } 

sysGlobalTmmStatServerMaxConns OBJECT-TYPE 
	SYNTAX Counter64
	MAX-ACCESS read-only
	STATUS current
	DESCRIPTION
		"The maximum connections from server-side to the system."
	::= { sysGlobalTmmStat 14 } 

sysGlobalTmmStatServerTotConns OBJECT-TYPE 
	SYNTAX Counter64
	MAX-ACCESS read-only
	STATUS current
	DESCRIPTION
		"The total connections from server-side to the system."
	::= { sysGlobalTmmStat 15 } 

sysGlobalTmmStatServerCurConns OBJECT-TYPE 
	SYNTAX CounterBasedGauge64
	MAX-ACCESS read-only
	STATUS current
	DESCRIPTION
		"The current connections from server-side to the system."
	::= { sysGlobalTmmStat 16 } 

sysGlobalTmmStatMaintenanceModeDeny OBJECT-TYPE 
	SYNTAX Counter64
	MAX-ACCESS read-only
	STATUS current
	DESCRIPTION
		"The connection requests rejected because the virtual
		server was in maintenance mode. "
	::= { sysGlobalTmmStat 17 } 

sysGlobalTmmStatMaxConnVirtualAddrDeny OBJECT-TYPE 
	SYNTAX Counter64
	MAX-ACCESS read-only
	STATUS current
	DESCRIPTION
		"The connection requests rejected because they exceeded
		the connection limit for a virtual server address."
	::= { sysGlobalTmmStat 18 } 

sysGlobalTmmStatMaxConnVirtualPathDeny OBJECT-TYPE 
	SYNTAX Counter64
	MAX-ACCESS read-only
	STATUS current
	DESCRIPTION
		"The connection requests rejected because they exceeded
		the connection limit for a virtual server (IP:port)."
	::= { sysGlobalTmmStat 19 } 

sysGlobalTmmStatVirtualServerNonSynDeny OBJECT-TYPE 
	SYNTAX Counter64
	MAX-ACCESS read-only
	STATUS current
	DESCRIPTION
		"The packets that are not connection requests and are 
		destined for a virtual server that has no connection 
		for the client address."
	::= { sysGlobalTmmStat 20 } 

sysGlobalTmmStatNoHandlerDeny OBJECT-TYPE 
	SYNTAX Counter64
	MAX-ACCESS read-only
	STATUS current
	DESCRIPTION
		"The incoming packets that could not be processed by a
		virtual server, NAT, or SNAT."
	::= { sysGlobalTmmStat 21 } 

sysGlobalTmmStatLicenseDeny OBJECT-TYPE 
	SYNTAX Counter64
	MAX-ACCESS read-only
	STATUS current
	DESCRIPTION
		"The packets which were dropped due to exceeding licensing 
		limitations."
	::= { sysGlobalTmmStat 22 } 

sysGlobalTmmStatCmpConnRedirected OBJECT-TYPE 
	SYNTAX Counter64
	MAX-ACCESS read-only
	STATUS current
	DESCRIPTION
		"The connections that were redirected to a different TMM in the cluster."
	::= { sysGlobalTmmStat 23 } 

sysGlobalTmmStatConnectionMemoryErrors OBJECT-TYPE 
	SYNTAX Counter64
	MAX-ACCESS read-only
	STATUS current
	DESCRIPTION
		"The connections could not be created because memory was not available."
	::= { sysGlobalTmmStat 24 } 

sysGlobalTmmStatTmTotalCycles OBJECT-TYPE 
	SYNTAX Counter64
	MAX-ACCESS read-only
	STATUS	 deprecated
	DESCRIPTION
		"Deprecated! Please use the provided tmm usage ratios.
		Traffic management CPU usage. The total cycles spent in traffic management."
	::= { sysGlobalTmmStat 25 } 

sysGlobalTmmStatTmIdleCycles OBJECT-TYPE 
	SYNTAX Counter64
	MAX-ACCESS read-only
	STATUS	 deprecated
	DESCRIPTION
		"Deprecated! Please use the provided tmm usage ratios.
		Traffic management CPU usage. The cycles spent polling with no traffic."
	::= { sysGlobalTmmStat 26 } 

sysGlobalTmmStatTmSleepCycles OBJECT-TYPE 
	SYNTAX Counter64
	MAX-ACCESS read-only
	STATUS	 deprecated
	DESCRIPTION
		"Deprecated! Please use the provided tmm usage ratios.
		Traffic management CPU usage. The cycles yielded."
	::= { sysGlobalTmmStat 27 } 

sysGlobalTmmStatMemoryTotal OBJECT-TYPE 
	SYNTAX CounterBasedGauge64
	MAX-ACCESS read-only
	STATUS current
	DESCRIPTION
		"The total memory available in bytes for TMM (Traffic Management Module)."
	::= { sysGlobalTmmStat 28 } 

sysGlobalTmmStatMemoryUsed OBJECT-TYPE 
	SYNTAX CounterBasedGauge64
	MAX-ACCESS read-only
	STATUS current
	DESCRIPTION
		"The memory in use in bytes for TMM (Traffic Management Module)."
	::= { sysGlobalTmmStat 29 } 

sysGlobalTmmStatDroppedPackets OBJECT-TYPE 
	SYNTAX Counter64
	MAX-ACCESS read-only
	STATUS current
	DESCRIPTION
		"The total dropped packets."
	::= { sysGlobalTmmStat 30 } 

sysGlobalTmmStatIncomingPacketErrors OBJECT-TYPE 
	SYNTAX Counter64
	MAX-ACCESS read-only
	STATUS current
	DESCRIPTION
		"The total incoming packet errors for the system."
	::= { sysGlobalTmmStat 31 } 

sysGlobalTmmStatOutgoingPacketErrors OBJECT-TYPE 
	SYNTAX Counter64
	MAX-ACCESS read-only
	STATUS current
	DESCRIPTION
		"The total outgoing packet errors for the system."
	::= { sysGlobalTmmStat 32 } 

sysGlobalTmmStatHttpRequests OBJECT-TYPE 
	SYNTAX Counter64
	MAX-ACCESS read-only
	STATUS current
	DESCRIPTION
		"The total number of HTTP requests to the system."
	::= { sysGlobalTmmStat 33 } 

sysGlobalTmmStatTmUsageRatio5s OBJECT-TYPE 
	SYNTAX CounterBasedGauge64
	MAX-ACCESS read-only
	STATUS current
	DESCRIPTION
		"The percentage of time all TMMs were busy over the last 5 seconds."
	::= { sysGlobalTmmStat 34 } 

sysGlobalTmmStatTmUsageRatio1m OBJECT-TYPE 
	SYNTAX CounterBasedGauge64
	MAX-ACCESS read-only
	STATUS current
	DESCRIPTION
		"The percentage of time all TMMs were busy over the last 1 minute."
	::= { sysGlobalTmmStat 35 } 

sysGlobalTmmStatTmUsageRatio5m OBJECT-TYPE 
	SYNTAX CounterBasedGauge64
	MAX-ACCESS read-only
	STATUS current
	DESCRIPTION
		"The percentage of time all TMMs were busy over the last 5 minutes."
	::= { sysGlobalTmmStat 36 } 

sysGlobalTmmStatMemoryTotalKb OBJECT-TYPE 
	SYNTAX CounterBasedGauge64
	MAX-ACCESS read-only
	STATUS current
	DESCRIPTION
		"The total memory available in Kilobytes for TMM (Traffic Management Module)."
	::= { sysGlobalTmmStat 37 } 

sysGlobalTmmStatMemoryUsedKb OBJECT-TYPE 
	SYNTAX CounterBasedGauge64
	MAX-ACCESS read-only
	STATUS current
	DESCRIPTION
		"The memory in use in Kilobytes for TMM (Traffic Management Module)."
	::= { sysGlobalTmmStat 38 } 

--==================================================================
-- Platform
--==================================================================
sysPlatformInfoName OBJECT-TYPE 
	SYNTAX LongDisplayString
	MAX-ACCESS read-only
	STATUS current
	DESCRIPTION
		"The platform name"
	::= { sysPlatformInfo 1 } 

sysPlatformInfoMarketingName OBJECT-TYPE 
	SYNTAX LongDisplayString
	MAX-ACCESS read-only
	STATUS current
	DESCRIPTION
		"The system name used by marketing"
	::= { sysPlatformInfo 2 } 

--==================================================================
-- Logical_disk
--==================================================================
sysLogicalDiskNumber OBJECT-TYPE 
	SYNTAX INTEGER
	MAX-ACCESS read-only
	STATUS current
	DESCRIPTION
		"The number of sysLogicalDisk entries in the table."
	::= { sysLogicalDisk 1 } 

sysLogicalDiskTable OBJECT-TYPE
	SYNTAX SEQUENCE OF SysLogicalDiskEntry
	MAX-ACCESS not-accessible
	STATUS current
	DESCRIPTION
		"Logical disks status"
	::= { sysLogicalDisk 2 } 

sysLogicalDiskEntry OBJECT-TYPE
	SYNTAX  SysLogicalDiskEntry
	MAX-ACCESS not-accessible
	STATUS current
	DESCRIPTION
		"Columns in the sysLogicalDisk Table"
	INDEX {
		sysLogicalDiskSlotId,
		sysLogicalDiskName
	}
	::= { sysLogicalDiskTable 1 } 

SysLogicalDiskEntry ::= 
	SEQUENCE {
        	sysLogicalDiskSlotId                                   INTEGER,
        	sysLogicalDiskName                                     LongDisplayString,
        	sysLogicalDiskDevname                                  LongDisplayString,
        	sysLogicalDiskMedia                                    LongDisplayString,
        	sysLogicalDiskSize                                     Integer32,
        	sysLogicalDiskFormat                                   LongDisplayString
	}

sysLogicalDiskSlotId OBJECT-TYPE 
	SYNTAX INTEGER(1..2147483647)
	MAX-ACCESS read-only
	STATUS current
	DESCRIPTION
		"The slot ID."
	::= { sysLogicalDiskEntry 1 } 

sysLogicalDiskName OBJECT-TYPE 
	SYNTAX LongDisplayString
	MAX-ACCESS read-only
	STATUS current
	DESCRIPTION
		"The logical disk name."
	::= { sysLogicalDiskEntry 2 } 

sysLogicalDiskDevname OBJECT-TYPE 
	SYNTAX LongDisplayString
	MAX-ACCESS read-only
	STATUS current
	DESCRIPTION
		"The logical disk device name."
	::= { sysLogicalDiskEntry 3 } 

sysLogicalDiskMedia OBJECT-TYPE 
	SYNTAX LongDisplayString
	MAX-ACCESS read-only
	STATUS current
	DESCRIPTION
		"The logical disk media."
	::= { sysLogicalDiskEntry 4 } 

sysLogicalDiskSize OBJECT-TYPE 
	SYNTAX Integer32
	MAX-ACCESS read-only
	STATUS current
	DESCRIPTION
		"The size of logical disk"
	::= { sysLogicalDiskEntry 5 } 

sysLogicalDiskFormat OBJECT-TYPE 
	SYNTAX LongDisplayString
	MAX-ACCESS read-only
	STATUS current
	DESCRIPTION
		"The logical disk formate."
	::= { sysLogicalDiskEntry 6 } 

--==================================================================
-- Physical_disk
--==================================================================
sysPhysicalDiskNumber OBJECT-TYPE 
	SYNTAX INTEGER
	MAX-ACCESS read-only
	STATUS current
	DESCRIPTION
		"The number of sysPhysicalDisk entries in the table."
	::= { sysPhysicalDisk 1 } 

sysPhysicalDiskTable OBJECT-TYPE
	SYNTAX SEQUENCE OF SysPhysicalDiskEntry
	MAX-ACCESS not-accessible
	STATUS current
	DESCRIPTION
		"Physical disk status"
	::= { sysPhysicalDisk 2 } 

sysPhysicalDiskEntry OBJECT-TYPE
	SYNTAX  SysPhysicalDiskEntry
	MAX-ACCESS not-accessible
	STATUS current
	DESCRIPTION
		"Columns in the sysPhysicalDisk Table"
	INDEX {
		sysPhysicalDiskSerialNumber
	}
	::= { sysPhysicalDiskTable 1 } 

SysPhysicalDiskEntry ::= 
	SEQUENCE {
        	sysPhysicalDiskSerialNumber                            LongDisplayString,
        	sysPhysicalDiskSlotId                                  INTEGER,
        	sysPhysicalDiskName                                    LongDisplayString,
        	sysPhysicalDiskIsArrayMember                           INTEGER,
        	sysPhysicalDiskArrayStatus                             INTEGER
	}

sysPhysicalDiskSerialNumber OBJECT-TYPE 
	SYNTAX LongDisplayString
	MAX-ACCESS read-only
	STATUS current
	DESCRIPTION
		"The serial number of physical disk"
	::= { sysPhysicalDiskEntry 1 } 

sysPhysicalDiskSlotId OBJECT-TYPE 
	SYNTAX INTEGER
	MAX-ACCESS read-only
	STATUS current
	DESCRIPTION
		"The slot ID."
	::= { sysPhysicalDiskEntry 2 } 

sysPhysicalDiskName OBJECT-TYPE 
	SYNTAX LongDisplayString
	MAX-ACCESS read-only
	STATUS current
	DESCRIPTION
		"The physical disk name."
	::= { sysPhysicalDiskEntry 3 } 

sysPhysicalDiskIsArrayMember OBJECT-TYPE 
	SYNTAX INTEGER {
		false(0),
		true(1)
	}
	MAX-ACCESS read-only
	STATUS current
	DESCRIPTION
		"If the physical disk is the member of an array. Default is false"
	::= { sysPhysicalDiskEntry 4 } 

sysPhysicalDiskArrayStatus OBJECT-TYPE 
	SYNTAX INTEGER {
		undefined(0),
		ok(1),
		replicating(2),
		missing(3),
		failed(4)
	}
	MAX-ACCESS read-only
	STATUS current
	DESCRIPTION
		"The physical disk array status"
	::= { sysPhysicalDiskEntry 5 } 

--==================================================================
-- Disk_bay
--==================================================================
sysDiskBayNumber OBJECT-TYPE 
	SYNTAX INTEGER
	MAX-ACCESS read-only
	STATUS current
	DESCRIPTION
		"The number of sysDiskBay entries in the table."
	::= { sysDiskBay 1 } 

sysDiskBayTable OBJECT-TYPE
	SYNTAX SEQUENCE OF SysDiskBayEntry
	MAX-ACCESS not-accessible
	STATUS current
	DESCRIPTION
		"Disk bay status"
	::= { sysDiskBay 2 } 

sysDiskBayEntry OBJECT-TYPE
	SYNTAX  SysDiskBayEntry
	MAX-ACCESS not-accessible
	STATUS current
	DESCRIPTION
		"Columns in the sysDiskBay Table"
	INDEX {
		sysDiskBayId
	}
	::= { sysDiskBayTable 1 } 

SysDiskBayEntry ::= 
	SEQUENCE {
        	sysDiskBayId                                           INTEGER,
        	sysDiskBayDiskSerialNumber                             LongDisplayString
	}

sysDiskBayId OBJECT-TYPE 
	SYNTAX INTEGER(1..2147483647)
	MAX-ACCESS read-only
	STATUS current
	DESCRIPTION
		"The disk bay ID."
	::= { sysDiskBayEntry 1 } 

sysDiskBayDiskSerialNumber OBJECT-TYPE 
	SYNTAX LongDisplayString
	MAX-ACCESS read-only
	STATUS current
	DESCRIPTION
		"The serial number of physical disk"
	::= { sysDiskBayEntry 2 } 

--==================================================================
-- Logical_disk_members
--==================================================================
sysLogicalDiskMembersNumber OBJECT-TYPE 
	SYNTAX INTEGER
	MAX-ACCESS read-only
	STATUS current
	DESCRIPTION
		"The number of sysLogicalDiskMembers entries in the table."
	::= { sysLogicalDiskMembers 1 } 

sysLogicalDiskMembersTable OBJECT-TYPE
	SYNTAX SEQUENCE OF SysLogicalDiskMembersEntry
	MAX-ACCESS not-accessible
	STATUS current
	DESCRIPTION
		"Logical disk members status"
	::= { sysLogicalDiskMembers 2 } 

sysLogicalDiskMembersEntry OBJECT-TYPE
	SYNTAX  SysLogicalDiskMembersEntry
	MAX-ACCESS not-accessible
	STATUS current
	DESCRIPTION
		"Columns in the sysLogicalDiskMembers Table"
	INDEX {
		sysLogicalDiskMembersDevname,
		sysLogicalDiskMembersSerialNumber
	}
	::= { sysLogicalDiskMembersTable 1 } 

SysLogicalDiskMembersEntry ::= 
	SEQUENCE {
        	sysLogicalDiskMembersDevname                           LongDisplayString,
        	sysLogicalDiskMembersSerialNumber                      LongDisplayString,
        	sysLogicalDiskMembersSlotId                            INTEGER
	}

sysLogicalDiskMembersDevname OBJECT-TYPE 
	SYNTAX LongDisplayString
	MAX-ACCESS read-only
	STATUS current
	DESCRIPTION
		"device name of logical disk members"
	::= { sysLogicalDiskMembersEntry 1 } 

sysLogicalDiskMembersSerialNumber OBJECT-TYPE 
	SYNTAX LongDisplayString
	MAX-ACCESS read-only
	STATUS current
	DESCRIPTION
		"The serial number of logical disk members"
	::= { sysLogicalDiskMembersEntry 2 } 

sysLogicalDiskMembersSlotId OBJECT-TYPE 
	SYNTAX INTEGER
	MAX-ACCESS read-only
	STATUS current
	DESCRIPTION
		"The slot ID of logical disk members."
	::= { sysLogicalDiskMembersEntry 3 } 

--==================================================================
-- Proc_pid_stat
--==================================================================
sysProcPidStatNumber OBJECT-TYPE 
	SYNTAX INTEGER
	MAX-ACCESS read-only
	STATUS current
	DESCRIPTION
		"The number of sysProcPidStat entries in the table."
	::= { sysProcPidStat 1 } 

sysProcPidStatTable OBJECT-TYPE
	SYNTAX SEQUENCE OF SysProcPidStatEntry
	MAX-ACCESS not-accessible
	STATUS current
	DESCRIPTION
		"individual process stat and statm"
	::= { sysProcPidStat 2 } 

sysProcPidStatEntry OBJECT-TYPE
	SYNTAX  SysProcPidStatEntry
	MAX-ACCESS not-accessible
	STATUS current
	DESCRIPTION
		"Columns in the sysProcPidStat Table"
	INDEX {
		sysProcPidStatPid
	}
	::= { sysProcPidStatTable 1 } 

SysProcPidStatEntry ::= 
	SEQUENCE {
        	sysProcPidStatPid                                      INTEGER,
        	sysProcPidStatProcName                                 LongDisplayString,
        	sysProcPidStatCommandLine                              LongDisplayString,
        	sysProcPidStatModules                                  LongDisplayString,
        	sysProcPidStatBladeNum                                 Integer32,
        	sysProcPidStatProcessor                                Integer32,
        	sysProcPidStatUpdateTime                               Integer32,
        	sysProcPidStatCpuUsageRecent                           Gauge,
        	sysProcPidStatCpuUsage1min                             Gauge,
        	sysProcPidStatCpuUsage5mins                            Gauge,
        	sysProcPidStatSystemUsageRecent                        Gauge,
        	sysProcPidStatSystemUsage1min                          Gauge,
        	sysProcPidStatSystemUsage5mins                         Gauge,
        	sysProcPidStatPpid                                     Integer32,
        	sysProcPidStatPgrp                                     Integer32,
        	sysProcPidStatState                                    LongDisplayString,
        	sysProcPidStatSession                                  Integer32,
        	sysProcPidStatTtyNr                                    Integer32,
        	sysProcPidStatTpgid                                    Integer32,
        	sysProcPidStatFlags                                    Counter64,
        	sysProcPidStatMinFlt                                   Counter64,
        	sysProcPidStatCminFlt                                  Counter64,
        	sysProcPidStatMajFlt                                   Counter64,
        	sysProcPidStatCmajFlt                                  Counter64,
        	sysProcPidStatUtime                                    Counter64,
        	sysProcPidStatStime                                    Counter64,
        	sysProcPidStatCutime                                   Counter64,
        	sysProcPidStatCstime                                   Counter64,
        	sysProcPidStatPriority                                 Integer32,
        	sysProcPidStatNice                                     Integer32,
        	sysProcPidStatNumThreads                               Integer32,
        	sysProcPidStatItrealvalue                              Integer32,
        	sysProcPidStatStartTime                                Counter64,
        	sysProcPidStatVsize                                    Counter64,
        	sysProcPidStatRss                                      Counter64,
        	sysProcPidStatRssRlim                                  Counter64,
        	sysProcPidStatStartCode                                Counter64,
        	sysProcPidStatEndCode                                  Counter64,
        	sysProcPidStatStartStack                               Counter64,
        	sysProcPidStatKstkEsp                                  Counter64,
        	sysProcPidStatKstkEip                                  Counter64,
        	sysProcPidStatSignal                                   Counter64,
        	sysProcPidStatBlocked                                  Counter64,
        	sysProcPidStatSigignore                                Counter64,
        	sysProcPidStatSigcatch                                 Counter64,
        	sysProcPidStatWchan                                    Counter64,
        	sysProcPidStatNswap                                    Counter64,
        	sysProcPidStatCnswap                                   Counter64,
        	sysProcPidStatExitSignal                               Integer32,
        	sysProcPidStatRtPriority                               Integer32,
        	sysProcPidStatPolicy                                   Integer32,
        	sysProcPidStatProgSize                                 Counter64,
        	sysProcPidStatResident                                 Counter64,
        	sysProcPidStatShare                                    Counter64,
        	sysProcPidStatTSize                                    Counter64,
        	sysProcPidStatLSize                                    Counter64,
        	sysProcPidStatDSize                                    Counter64,
        	sysProcPidStatDirty                                    Counter64
	}

sysProcPidStatPid OBJECT-TYPE 
	SYNTAX INTEGER(1..2147483647)
	MAX-ACCESS read-only
	STATUS current
	DESCRIPTION
		"process pid"
	::= { sysProcPidStatEntry 1 } 

sysProcPidStatProcName OBJECT-TYPE 
	SYNTAX LongDisplayString
	MAX-ACCESS read-only
	STATUS current
	DESCRIPTION
		"process name"
	::= { sysProcPidStatEntry 2 } 

sysProcPidStatCommandLine OBJECT-TYPE 
	SYNTAX LongDisplayString
	MAX-ACCESS read-only
	STATUS current
	DESCRIPTION
		"command line used to start process"
	::= { sysProcPidStatEntry 3 } 

sysProcPidStatModules OBJECT-TYPE 
	SYNTAX LongDisplayString
	MAX-ACCESS read-only
	STATUS current
	DESCRIPTION
		"module name of this process"
	::= { sysProcPidStatEntry 4 } 

sysProcPidStatBladeNum OBJECT-TYPE 
	SYNTAX Integer32
	MAX-ACCESS read-only
	STATUS current
	DESCRIPTION
		"blade number"
	::= { sysProcPidStatEntry 5 } 

sysProcPidStatProcessor OBJECT-TYPE 
	SYNTAX Integer32
	MAX-ACCESS read-only
	STATUS current
	DESCRIPTION
		"last CPU process run on"
	::= { sysProcPidStatEntry 6 } 

sysProcPidStatUpdateTime OBJECT-TYPE 
	SYNTAX Integer32
	MAX-ACCESS read-only
	STATUS current
	DESCRIPTION
		"last time proc_pid_stat updated"
	::= { sysProcPidStatEntry 7 } 

sysProcPidStatCpuUsageRecent OBJECT-TYPE 
	SYNTAX Gauge
	MAX-ACCESS read-only
	STATUS current
	DESCRIPTION
		"last poll interval cpu usage (percentage)"
	::= { sysProcPidStatEntry 8 } 

sysProcPidStatCpuUsage1min OBJECT-TYPE 
	SYNTAX Gauge
	MAX-ACCESS read-only
	STATUS current
	DESCRIPTION
		"last 1 min average cpu usage (percentage)"
	::= { sysProcPidStatEntry 9 } 

sysProcPidStatCpuUsage5mins OBJECT-TYPE 
	SYNTAX Gauge
	MAX-ACCESS read-only
	STATUS current
	DESCRIPTION
		"last 5 mins average cpu usage (percentage)"
	::= { sysProcPidStatEntry 10 } 

sysProcPidStatSystemUsageRecent OBJECT-TYPE 
	SYNTAX Gauge
	MAX-ACCESS read-only
	STATUS current
	DESCRIPTION
		"last poll interval system usage (percentage)"
	::= { sysProcPidStatEntry 11 } 

sysProcPidStatSystemUsage1min OBJECT-TYPE 
	SYNTAX Gauge
	MAX-ACCESS read-only
	STATUS current
	DESCRIPTION
		"last 1 min average system usage (percentage)"
	::= { sysProcPidStatEntry 12 } 

sysProcPidStatSystemUsage5mins OBJECT-TYPE 
	SYNTAX Gauge
	MAX-ACCESS read-only
	STATUS current
	DESCRIPTION
		"last 5 mins average system usage (percentage)"
	::= { sysProcPidStatEntry 13 } 

sysProcPidStatPpid OBJECT-TYPE 
	SYNTAX Integer32
	MAX-ACCESS read-only
	STATUS current
	DESCRIPTION
		"pid of process parent"
	::= { sysProcPidStatEntry 14 } 

sysProcPidStatPgrp OBJECT-TYPE 
	SYNTAX Integer32
	MAX-ACCESS read-only
	STATUS current
	DESCRIPTION
		"process group id"
	::= { sysProcPidStatEntry 15 } 

sysProcPidStatState OBJECT-TYPE 
	SYNTAX LongDisplayString
	MAX-ACCESS read-only
	STATUS current
	DESCRIPTION
		"single-char code for process state (S=sleep)"
	::= { sysProcPidStatEntry 16 } 

sysProcPidStatSession OBJECT-TYPE 
	SYNTAX Integer32
	MAX-ACCESS read-only
	STATUS current
	DESCRIPTION
		"session id"
	::= { sysProcPidStatEntry 17 } 

sysProcPidStatTtyNr OBJECT-TYPE 
	SYNTAX Integer32
	MAX-ACCESS read-only
	STATUS current
	DESCRIPTION
		"full device number of controlling terminal"
	::= { sysProcPidStatEntry 18 } 

sysProcPidStatTpgid OBJECT-TYPE 
	SYNTAX Integer32
	MAX-ACCESS read-only
	STATUS current
	DESCRIPTION
		"terminal process group id"
	::= { sysProcPidStatEntry 19 } 

sysProcPidStatFlags OBJECT-TYPE 
	SYNTAX Counter64
	MAX-ACCESS read-only
	STATUS current
	DESCRIPTION
		"kernel flags for the process"
	::= { sysProcPidStatEntry 20 } 

sysProcPidStatMinFlt OBJECT-TYPE 
	SYNTAX Counter64
	MAX-ACCESS read-only
	STATUS current
	DESCRIPTION
		"num minor pg faults since process start"
	::= { sysProcPidStatEntry 21 } 

sysProcPidStatCminFlt OBJECT-TYPE 
	SYNTAX Counter64
	MAX-ACCESS read-only
	STATUS current
	DESCRIPTION
		"num minor pg faults of child processes"
	::= { sysProcPidStatEntry 22 } 

sysProcPidStatMajFlt OBJECT-TYPE 
	SYNTAX Counter64
	MAX-ACCESS read-only
	STATUS current
	DESCRIPTION
		"num major pg faults since process start"
	::= { sysProcPidStatEntry 23 } 

sysProcPidStatCmajFlt OBJECT-TYPE 
	SYNTAX Counter64
	MAX-ACCESS read-only
	STATUS current
	DESCRIPTION
		"num major pg faults of child processes"
	::= { sysProcPidStatEntry 24 } 

sysProcPidStatUtime OBJECT-TYPE 
	SYNTAX Counter64
	MAX-ACCESS read-only
	STATUS current
	DESCRIPTION
		"user-mode CPU time accumulated by process"
	::= { sysProcPidStatEntry 25 } 

sysProcPidStatStime OBJECT-TYPE 
	SYNTAX Counter64
	MAX-ACCESS read-only
	STATUS current
	DESCRIPTION
		"kernel-mode CPU time accumulated by process"
	::= { sysProcPidStatEntry 26 } 

sysProcPidStatCutime OBJECT-TYPE 
	SYNTAX Counter64
	MAX-ACCESS read-only
	STATUS current
	DESCRIPTION
		"cumul utime of process + reaped children"
	::= { sysProcPidStatEntry 27 } 

sysProcPidStatCstime OBJECT-TYPE 
	SYNTAX Counter64
	MAX-ACCESS read-only
	STATUS current
	DESCRIPTION
		"cumul stime of process + reaped children"
	::= { sysProcPidStatEntry 28 } 

sysProcPidStatPriority OBJECT-TYPE 
	SYNTAX Integer32
	MAX-ACCESS read-only
	STATUS current
	DESCRIPTION
		"kernel scheduling priority"
	::= { sysProcPidStatEntry 29 } 

sysProcPidStatNice OBJECT-TYPE 
	SYNTAX Integer32
	MAX-ACCESS read-only
	STATUS current
	DESCRIPTION
		"standard unix nice level of process"
	::= { sysProcPidStatEntry 30 } 

sysProcPidStatNumThreads OBJECT-TYPE 
	SYNTAX Integer32
	MAX-ACCESS read-only
	STATUS current
	DESCRIPTION
		"Number of threads in this process"
	::= { sysProcPidStatEntry 31 } 

sysProcPidStatItrealvalue OBJECT-TYPE 
	SYNTAX Integer32
	MAX-ACCESS read-only
	STATUS current
	DESCRIPTION
		"Time in jiffies before next SIGALRM sent"
	::= { sysProcPidStatEntry 32 } 

sysProcPidStatStartTime OBJECT-TYPE 
	SYNTAX Counter64
	MAX-ACCESS read-only
	STATUS current
	DESCRIPTION
		"start time of process - sec since 1-1-70"
	::= { sysProcPidStatEntry 33 } 

sysProcPidStatVsize OBJECT-TYPE 
	SYNTAX Counter64
	MAX-ACCESS read-only
	STATUS current
	DESCRIPTION
		"number of pages of virtual memory ..."
	::= { sysProcPidStatEntry 34 } 

sysProcPidStatRss OBJECT-TYPE 
	SYNTAX Counter64
	MAX-ACCESS read-only
	STATUS current
	DESCRIPTION
		"resident set size (pg)"
	::= { sysProcPidStatEntry 35 } 

sysProcPidStatRssRlim OBJECT-TYPE 
	SYNTAX Counter64
	MAX-ACCESS read-only
	STATUS current
	DESCRIPTION
		"resident set size limit"
	::= { sysProcPidStatEntry 36 } 

sysProcPidStatStartCode OBJECT-TYPE 
	SYNTAX Counter64
	MAX-ACCESS read-only
	STATUS current
	DESCRIPTION
		"address of beginning of code segment"
	::= { sysProcPidStatEntry 37 } 

sysProcPidStatEndCode OBJECT-TYPE 
	SYNTAX Counter64
	MAX-ACCESS read-only
	STATUS current
	DESCRIPTION
		"address of end of code segment"
	::= { sysProcPidStatEntry 38 } 

sysProcPidStatStartStack OBJECT-TYPE 
	SYNTAX Counter64
	MAX-ACCESS read-only
	STATUS current
	DESCRIPTION
		"addr of the bottom of stack for process"
	::= { sysProcPidStatEntry 39 } 

sysProcPidStatKstkEsp OBJECT-TYPE 
	SYNTAX Counter64
	MAX-ACCESS read-only
	STATUS current
	DESCRIPTION
		"kernel stack pointer"
	::= { sysProcPidStatEntry 40 } 

sysProcPidStatKstkEip OBJECT-TYPE 
	SYNTAX Counter64
	MAX-ACCESS read-only
	STATUS current
	DESCRIPTION
		"kernel instruction pointer"
	::= { sysProcPidStatEntry 41 } 

sysProcPidStatSignal OBJECT-TYPE 
	SYNTAX Counter64
	MAX-ACCESS read-only
	STATUS current
	DESCRIPTION
		"bit map of pending signals"
	::= { sysProcPidStatEntry 42 } 

sysProcPidStatBlocked OBJECT-TYPE 
	SYNTAX Counter64
	MAX-ACCESS read-only
	STATUS current
	DESCRIPTION
		"mask of blocked signals"
	::= { sysProcPidStatEntry 43 } 

sysProcPidStatSigignore OBJECT-TYPE 
	SYNTAX Counter64
	MAX-ACCESS read-only
	STATUS current
	DESCRIPTION
		"mask of ignored signals"
	::= { sysProcPidStatEntry 44 } 

sysProcPidStatSigcatch OBJECT-TYPE 
	SYNTAX Counter64
	MAX-ACCESS read-only
	STATUS current
	DESCRIPTION
		"mask of caught  signals"
	::= { sysProcPidStatEntry 45 } 

sysProcPidStatWchan OBJECT-TYPE 
	SYNTAX Counter64
	MAX-ACCESS read-only
	STATUS current
	DESCRIPTION
		"address of kernel wait channel proc is"
	::= { sysProcPidStatEntry 46 } 

sysProcPidStatNswap OBJECT-TYPE 
	SYNTAX Counter64
	MAX-ACCESS read-only
	STATUS current
	DESCRIPTION
		"number of page swapped"
	::= { sysProcPidStatEntry 47 } 

sysProcPidStatCnswap OBJECT-TYPE 
	SYNTAX Counter64
	MAX-ACCESS read-only
	STATUS current
	DESCRIPTION
		"cumulative number of page swapped"
	::= { sysProcPidStatEntry 48 } 

sysProcPidStatExitSignal OBJECT-TYPE 
	SYNTAX Integer32
	MAX-ACCESS read-only
	STATUS current
	DESCRIPTION
		"might not be SIGCHLD"
	::= { sysProcPidStatEntry 49 } 

sysProcPidStatRtPriority OBJECT-TYPE 
	SYNTAX Integer32
	MAX-ACCESS read-only
	STATUS current
	DESCRIPTION
		"real-time priority"
	::= { sysProcPidStatEntry 50 } 

sysProcPidStatPolicy OBJECT-TYPE 
	SYNTAX Integer32
	MAX-ACCESS read-only
	STATUS current
	DESCRIPTION
		"schedule policy"
	::= { sysProcPidStatEntry 51 } 

sysProcPidStatProgSize OBJECT-TYPE 
	SYNTAX Counter64
	MAX-ACCESS read-only
	STATUS current
	DESCRIPTION
		"total program size"
	::= { sysProcPidStatEntry 52 } 

sysProcPidStatResident OBJECT-TYPE 
	SYNTAX Counter64
	MAX-ACCESS read-only
	STATUS current
	DESCRIPTION
		"resident size"
	::= { sysProcPidStatEntry 53 } 

sysProcPidStatShare OBJECT-TYPE 
	SYNTAX Counter64
	MAX-ACCESS read-only
	STATUS current
	DESCRIPTION
		"shared pages"
	::= { sysProcPidStatEntry 54 } 

sysProcPidStatTSize OBJECT-TYPE 
	SYNTAX Counter64
	MAX-ACCESS read-only
	STATUS current
	DESCRIPTION
		"text (code)"
	::= { sysProcPidStatEntry 55 } 

sysProcPidStatLSize OBJECT-TYPE 
	SYNTAX Counter64
	MAX-ACCESS read-only
	STATUS current
	DESCRIPTION
		"library, not used in Linux 2.6"
	::= { sysProcPidStatEntry 56 } 

sysProcPidStatDSize OBJECT-TYPE 
	SYNTAX Counter64
	MAX-ACCESS read-only
	STATUS current
	DESCRIPTION
		"data + stack, not used in Linux 2.6"
	::= { sysProcPidStatEntry 57 } 

sysProcPidStatDirty OBJECT-TYPE 
	SYNTAX Counter64
	MAX-ACCESS read-only
	STATUS current
	DESCRIPTION
		"dirty pages, not used in Linux 2.6"
	::= { sysProcPidStatEntry 58 } 

--==================================================================
-- Global_httpcompression_stat
--==================================================================
sysHttpCompressionStatResetStats OBJECT-TYPE 
	SYNTAX INTEGER
	MAX-ACCESS read-write
	STATUS current
	DESCRIPTION
		"The action to reset resetable statistics data in  sysGlobalHttpCompressionStat. 
		 Setting this value to 1 will reset statistics data. 
		 Note, some statistics data may not be reset including data that are incremental counters."
	::= { sysGlobalHttpCompressionStat 1 } 

sysHttpCompressionStatPrecompressBytes OBJECT-TYPE 
	SYNTAX Counter64
	MAX-ACCESS read-only
	STATUS current
	DESCRIPTION
		"The number of response bytes before compression has taken place."
	::= { sysGlobalHttpCompressionStat 2 } 

sysHttpCompressionStatPostcompressBytes OBJECT-TYPE 
	SYNTAX Counter64
	MAX-ACCESS read-only
	STATUS current
	DESCRIPTION
		"The number of response bytes after compression has taken place."
	::= { sysGlobalHttpCompressionStat 3 } 

sysHttpCompressionStatNullCompressBytes OBJECT-TYPE 
	SYNTAX Counter64
	MAX-ACCESS read-only
	STATUS current
	DESCRIPTION
		"The number of bytes subjected to NULL compression (for license enforcement)."
	::= { sysGlobalHttpCompressionStat 4 } 

sysHttpCompressionStatHtmlPrecompressBytes OBJECT-TYPE 
	SYNTAX Counter64
	MAX-ACCESS read-only
	STATUS current
	DESCRIPTION
		"The number of pre-compressed bytes for the MIME-Types: HTML."
	::= { sysGlobalHttpCompressionStat 5 } 

sysHttpCompressionStatHtmlPostcompressBytes OBJECT-TYPE 
	SYNTAX Counter64
	MAX-ACCESS read-only
	STATUS current
	DESCRIPTION
		"The number of post-compressed bytes for the MIME-Types: HTML."
	::= { sysGlobalHttpCompressionStat 6 } 

sysHttpCompressionStatCssPrecompressBytes OBJECT-TYPE 
	SYNTAX Counter64
	MAX-ACCESS read-only
	STATUS current
	DESCRIPTION
		"The number of pre-compressed bytes for the MIME-Types: CSS."
	::= { sysGlobalHttpCompressionStat 7 } 

sysHttpCompressionStatCssPostcompressBytes OBJECT-TYPE 
	SYNTAX Counter64
	MAX-ACCESS read-only
	STATUS current
	DESCRIPTION
		"The number of post-compressed bytes for the MIME-Types: CSS."
	::= { sysGlobalHttpCompressionStat 8 } 

sysHttpCompressionStatJsPrecompressBytes OBJECT-TYPE 
	SYNTAX Counter64
	MAX-ACCESS read-only
	STATUS current
	DESCRIPTION
		"The number of pre-compressed bytes for the MIME-Types: Javascript."
	::= { sysGlobalHttpCompressionStat 9 } 

sysHttpCompressionStatJsPostcompressBytes OBJECT-TYPE 
	SYNTAX Counter64
	MAX-ACCESS read-only
	STATUS current
	DESCRIPTION
		"The number of post-compressed bytes for the MIME-Types: Javascript."
	::= { sysGlobalHttpCompressionStat 10 } 

sysHttpCompressionStatXmlPrecompressBytes OBJECT-TYPE 
	SYNTAX Counter64
	MAX-ACCESS read-only
	STATUS current
	DESCRIPTION
		"The number of pre-compressed bytes for the MIME-Types: XML."
	::= { sysGlobalHttpCompressionStat 11 } 

sysHttpCompressionStatXmlPostcompressBytes OBJECT-TYPE 
	SYNTAX Counter64
	MAX-ACCESS read-only
	STATUS current
	DESCRIPTION
		"The number of post-compressed bytes for the MIME-Types: XML."
	::= { sysGlobalHttpCompressionStat 12 } 

sysHttpCompressionStatSgmlPrecompressBytes OBJECT-TYPE 
	SYNTAX Counter64
	MAX-ACCESS read-only
	STATUS current
	DESCRIPTION
		"The number of pre-compressed bytes for the MIME-Types: SGML."
	::= { sysGlobalHttpCompressionStat 13 } 

sysHttpCompressionStatSgmlPostcompressBytes OBJECT-TYPE 
	SYNTAX Counter64
	MAX-ACCESS read-only
	STATUS current
	DESCRIPTION
		"The number of post-compressed bytes for the MIME-Types: SGML."
	::= { sysGlobalHttpCompressionStat 14 } 

sysHttpCompressionStatPlainPrecompressBytes OBJECT-TYPE 
	SYNTAX Counter64
	MAX-ACCESS read-only
	STATUS current
	DESCRIPTION
		"The number of pre-compressed bytes for the MIME-Types: Plain."
	::= { sysGlobalHttpCompressionStat 15 } 

sysHttpCompressionStatPlainPostcompressBytes OBJECT-TYPE 
	SYNTAX Counter64
	MAX-ACCESS read-only
	STATUS current
	DESCRIPTION
		"The number of post-compressed bytes for the MIME-Types: Plain."
	::= { sysGlobalHttpCompressionStat 16 } 

sysHttpCompressionStatOctetPrecompressBytes OBJECT-TYPE 
	SYNTAX Counter64
	MAX-ACCESS read-only
	STATUS current
	DESCRIPTION
		"The number of pre-compressed bytes for the MIME-Types: Octet stream."
	::= { sysGlobalHttpCompressionStat 17 } 

sysHttpCompressionStatOctetPostcompressBytes OBJECT-TYPE 
	SYNTAX Counter64
	MAX-ACCESS read-only
	STATUS current
	DESCRIPTION
		"The number of post-compressed bytes for the MIME-Types: Octet stream."
	::= { sysGlobalHttpCompressionStat 18 } 

sysHttpCompressionStatImagePrecompressBytes OBJECT-TYPE 
	SYNTAX Counter64
	MAX-ACCESS read-only
	STATUS current
	DESCRIPTION
		"The number of pre-compressed bytes for the MIME-Types: Images."
	::= { sysGlobalHttpCompressionStat 19 } 

sysHttpCompressionStatImagePostcompressBytes OBJECT-TYPE 
	SYNTAX Counter64
	MAX-ACCESS read-only
	STATUS current
	DESCRIPTION
		"The number of post-compressed bytes for the MIME-Types: Images."
	::= { sysGlobalHttpCompressionStat 20 } 

sysHttpCompressionStatVideoPrecompressBytes OBJECT-TYPE 
	SYNTAX Counter64
	MAX-ACCESS read-only
	STATUS current
	DESCRIPTION
		"The number of pre-compressed bytes for the MIME-Types: Video files."
	::= { sysGlobalHttpCompressionStat 21 } 

sysHttpCompressionStatVideoPostcompressBytes OBJECT-TYPE 
	SYNTAX Counter64
	MAX-ACCESS read-only
	STATUS current
	DESCRIPTION
		"The number of post-compressed bytes for the MIME-Types: Video files."
	::= { sysGlobalHttpCompressionStat 22 } 

sysHttpCompressionStatAudioPrecompressBytes OBJECT-TYPE 
	SYNTAX Counter64
	MAX-ACCESS read-only
	STATUS current
	DESCRIPTION
		"The number of pre-compressed bytes for the MIME-Types: Audio files."
	::= { sysGlobalHttpCompressionStat 23 } 

sysHttpCompressionStatAudioPostcompressBytes OBJECT-TYPE 
	SYNTAX Counter64
	MAX-ACCESS read-only
	STATUS current
	DESCRIPTION
		"The number of post-compressed bytes for the MIME-Types: Audio files."
	::= { sysGlobalHttpCompressionStat 24 } 

sysHttpCompressionStatOtherPrecompressBytes OBJECT-TYPE 
	SYNTAX Counter64
	MAX-ACCESS read-only
	STATUS current
	DESCRIPTION
		"The number of pre-compressed bytes for the MIME-Types: other than 
		HTML, CSS, Javascript, XML, SGML, Plain, Images, Video files, 
		Audio files."
	::= { sysGlobalHttpCompressionStat 25 } 

sysHttpCompressionStatOtherPostcompressBytes OBJECT-TYPE 
	SYNTAX Counter64
	MAX-ACCESS read-only
	STATUS current
	DESCRIPTION
		"The number of post-compressed bytes for the MIME-Types: other than 
		HTML, CSS, Javascript, XML, SGML, Plain, Images, Video files, 
		Audio files."
	::= { sysGlobalHttpCompressionStat 26 } 

--==================================================================
-- Global_webacceleration_stat
--==================================================================
sysWebAccelerationStatResetStats OBJECT-TYPE 
	SYNTAX INTEGER
	MAX-ACCESS read-write
	STATUS current
	DESCRIPTION
		"The action to reset resetable statistics data in  sysGlobalWebAccelerationStat. 
		 Setting this value to 1 will reset statistics data. 
		 Note, some statistics data may not be reset including data that are incremental counters."
	::= { sysGlobalWebAccelerationStat 1 } 

sysWebAccelerationStatCacheHits OBJECT-TYPE 
	SYNTAX Counter64
	MAX-ACCESS read-only
	STATUS current
	DESCRIPTION
		"The number of cache hits."
	::= { sysGlobalWebAccelerationStat 2 } 

sysWebAccelerationStatCacheMisses OBJECT-TYPE 
	SYNTAX Counter64
	MAX-ACCESS read-only
	STATUS current
	DESCRIPTION
		"The number of cache misses, excluding un-cacheable data."
	::= { sysGlobalWebAccelerationStat 3 } 

sysWebAccelerationStatCacheMissesAll OBJECT-TYPE 
	SYNTAX Counter64
	MAX-ACCESS read-only
	STATUS current
	DESCRIPTION
		"The total number of cache misses."
	::= { sysGlobalWebAccelerationStat 4 } 

sysWebAccelerationStatCacheHitBytes OBJECT-TYPE 
	SYNTAX Counter64
	MAX-ACCESS read-only
	STATUS current
	DESCRIPTION
		"The number of cache hits in bytes."
	::= { sysGlobalWebAccelerationStat 5 } 

sysWebAccelerationStatCacheMissBytes OBJECT-TYPE 
	SYNTAX Counter64
	MAX-ACCESS read-only
	STATUS current
	DESCRIPTION
		"The number of cache misses in bytes, excluding un-cacheable data."
	::= { sysGlobalWebAccelerationStat 6 } 

sysWebAccelerationStatCacheMissBytesAll OBJECT-TYPE 
	SYNTAX Counter64
	MAX-ACCESS read-only
	STATUS current
	DESCRIPTION
		"The total number of cache misses in bytes."
	::= { sysGlobalWebAccelerationStat 7 } 

sysWebAccelerationStatCacheSize OBJECT-TYPE 
	SYNTAX Counter64
	MAX-ACCESS read-only
	STATUS current
	DESCRIPTION
		"The current cache size (in bytes)."
	::= { sysGlobalWebAccelerationStat 8 } 

sysWebAccelerationStatCacheCount OBJECT-TYPE 
	SYNTAX Counter64
	MAX-ACCESS read-only
	STATUS current
	DESCRIPTION
		"The number of items stored in cache."
	::= { sysGlobalWebAccelerationStat 9 } 

sysWebAccelerationStatCacheEvictions OBJECT-TYPE 
	SYNTAX Counter64
	MAX-ACCESS read-only
	STATUS current
	DESCRIPTION
		"The number of cache evictions."
	::= { sysGlobalWebAccelerationStat 10 } 

sysWebAccelerationStatInterStripeHits OBJECT-TYPE 
	SYNTAX Counter64
	MAX-ACCESS read-only
	STATUS current
	DESCRIPTION
		"The number of inter-stripe cache hits."
	::= { sysGlobalWebAccelerationStat 11 } 

sysWebAccelerationStatInterStripeMisses OBJECT-TYPE 
	SYNTAX Counter64
	MAX-ACCESS read-only
	STATUS current
	DESCRIPTION
		"The number of inter-stripe cache misses."
	::= { sysGlobalWebAccelerationStat 12 } 

sysWebAccelerationStatInterStripeHitBytes OBJECT-TYPE 
	SYNTAX Counter64
	MAX-ACCESS read-only
	STATUS current
	DESCRIPTION
		"The number of inter-stripe cache hits in bytes."
	::= { sysGlobalWebAccelerationStat 13 } 

sysWebAccelerationStatInterStripeSize OBJECT-TYPE 
	SYNTAX Counter64
	MAX-ACCESS read-only
	STATUS current
	DESCRIPTION
		"The current inter-stripe cache size (in bytes)."
	::= { sysGlobalWebAccelerationStat 14 } 

sysWebAccelerationStatInterStripeCount OBJECT-TYPE 
	SYNTAX Counter64
	MAX-ACCESS read-only
	STATUS current
	DESCRIPTION
		"The number of items stored in inter-stripe cache."
	::= { sysGlobalWebAccelerationStat 15 } 

sysWebAccelerationStatInterStripeEvictions OBJECT-TYPE 
	SYNTAX Counter64
	MAX-ACCESS read-only
	STATUS current
	DESCRIPTION
		"The number of inter-stripe cache evictions."
	::= { sysGlobalWebAccelerationStat 16 } 

sysWebAccelerationStatRemoteHits OBJECT-TYPE 
	SYNTAX Counter64
	MAX-ACCESS read-only
	STATUS current
	DESCRIPTION
		"The number of remote cache hits."
	::= { sysGlobalWebAccelerationStat 17 } 

sysWebAccelerationStatRemoteMisses OBJECT-TYPE 
	SYNTAX Counter64
	MAX-ACCESS read-only
	STATUS current
	DESCRIPTION
		"The number of remote cache misses."
	::= { sysGlobalWebAccelerationStat 18 } 

sysWebAccelerationStatRemoteHitBytes OBJECT-TYPE 
	SYNTAX Counter64
	MAX-ACCESS read-only
	STATUS current
	DESCRIPTION
		"The number of remote cache hits in bytes."
	::= { sysGlobalWebAccelerationStat 19 } 

--==================================================================
-- Vlan_stat
--==================================================================
sysVlanStatNumber OBJECT-TYPE 
	SYNTAX INTEGER
	MAX-ACCESS read-only
	STATUS current
	DESCRIPTION
		"The number of sysVlanStat entries in the table."
	::= { sysVlanStat 1 } 

sysVlanStatTable OBJECT-TYPE
	SYNTAX SEQUENCE OF SysVlanStatEntry
	MAX-ACCESS not-accessible
	STATUS current
	DESCRIPTION
		"Vlan statistics, sum of its interfaces interface_stat."
	::= { sysVlanStat 2 } 

sysVlanStatEntry OBJECT-TYPE
	SYNTAX  SysVlanStatEntry
	MAX-ACCESS not-accessible
	STATUS current
	DESCRIPTION
		"Columns in the sysVlanStat Table"
	INDEX {
		sysVlanStatVlanName
	}
	::= { sysVlanStatTable 1 } 

SysVlanStatEntry ::= 
	SEQUENCE {
        	sysVlanStatVlanName                                    LongDisplayString,
        	sysVlanStatPktsIn                                      Counter64,
        	sysVlanStatBytesIn                                     Counter64,
        	sysVlanStatPktsOut                                     Counter64,
        	sysVlanStatBytesOut                                    Counter64,
        	sysVlanStatMcastIn                                     Counter64,
        	sysVlanStatMcastOut                                    Counter64,
        	sysVlanStatErrorsIn                                    Counter64,
        	sysVlanStatErrorsOut                                   Counter64,
        	sysVlanStatDropsIn                                     Counter64,
        	sysVlanStatDropsOut                                    Counter64,
        	sysVlanStatCollisions                                  Counter64
	}

sysVlanStatVlanName OBJECT-TYPE 
	SYNTAX LongDisplayString
	MAX-ACCESS read-only
	STATUS current
	DESCRIPTION
		"The name of a VLAN."
	::= { sysVlanStatEntry 1 } 

sysVlanStatPktsIn OBJECT-TYPE 
	SYNTAX Counter64
	MAX-ACCESS read-only
	STATUS current
	DESCRIPTION
		"The number of packets received on this vlan."
	::= { sysVlanStatEntry 2 } 

sysVlanStatBytesIn OBJECT-TYPE 
	SYNTAX Counter64
	MAX-ACCESS read-only
	STATUS current
	DESCRIPTION
		"The number of bytes received on the specified vlan."
	::= { sysVlanStatEntry 3 } 

sysVlanStatPktsOut OBJECT-TYPE 
	SYNTAX Counter64
	MAX-ACCESS read-only
	STATUS current
	DESCRIPTION
		"The number of packets transmitted out of the specified vlan."
	::= { sysVlanStatEntry 4 } 

sysVlanStatBytesOut OBJECT-TYPE 
	SYNTAX Counter64
	MAX-ACCESS read-only
	STATUS current
	DESCRIPTION
		"The number of bytes transmitted out of the specified vlan."
	::= { sysVlanStatEntry 5 } 

sysVlanStatMcastIn OBJECT-TYPE 
	SYNTAX Counter64
	MAX-ACCESS read-only
	STATUS current
	DESCRIPTION
		"The number of multicast packets received on the specified vlan."
	::= { sysVlanStatEntry 6 } 

sysVlanStatMcastOut OBJECT-TYPE 
	SYNTAX Counter64
	MAX-ACCESS read-only
	STATUS current
	DESCRIPTION
		"The number of multicast packets transmitted out of the specified vlan."
	::= { sysVlanStatEntry 7 } 

sysVlanStatErrorsIn OBJECT-TYPE 
	SYNTAX Counter64
	MAX-ACCESS read-only
	STATUS current
	DESCRIPTION
		"The number of received packets that are either undersized, 
		oversized, or have FCS errors by the specified vlan."
	::= { sysVlanStatEntry 8 } 

sysVlanStatErrorsOut OBJECT-TYPE 
	SYNTAX Counter64
	MAX-ACCESS read-only
	STATUS current
	DESCRIPTION
		"The number of excessive collisions, incremented for each 
		frame that experienced 16 collisions during transmission and 
		was aborted on the specified vlan."
	::= { sysVlanStatEntry 9 } 

sysVlanStatDropsIn OBJECT-TYPE 
	SYNTAX Counter64
	MAX-ACCESS read-only
	STATUS current
	DESCRIPTION
		"The number of packets dropped on ingress for various reasons on the specified vlan."
	::= { sysVlanStatEntry 10 } 

sysVlanStatDropsOut OBJECT-TYPE 
	SYNTAX Counter64
	MAX-ACCESS read-only
	STATUS current
	DESCRIPTION
		"The number of packets aged out or with excessive transmission 
		delays due to multiple deferrals on the specified vlan."
	::= { sysVlanStatEntry 11 } 

sysVlanStatCollisions OBJECT-TYPE 
	SYNTAX Counter64
	MAX-ACCESS read-only
	STATUS current
	DESCRIPTION
		"The number of collisions on the specified vlan, incremented by the 
		number of collisions experienced during transmissions of a frame"
	::= { sysVlanStatEntry 12 } 

--==================================================================
-- Vlanx_stat
--==================================================================
sysVlanxStatNumber OBJECT-TYPE 
	SYNTAX INTEGER
	MAX-ACCESS read-only
	STATUS current
	DESCRIPTION
		"The number of sysVlanxStat entries in the table."
	::= { sysVlanxStat 1 } 

sysVlanxStatTable OBJECT-TYPE
	SYNTAX SEQUENCE OF SysVlanxStatEntry
	MAX-ACCESS not-accessible
	STATUS current
	DESCRIPTION
		"Vlan statistics, sum of its interfaces ifx_stat."
	::= { sysVlanxStat 2 } 

sysVlanxStatEntry OBJECT-TYPE
	SYNTAX  SysVlanxStatEntry
	MAX-ACCESS not-accessible
	STATUS current
	DESCRIPTION
		"Columns in the sysVlanxStat Table"
	INDEX {
		sysVlanxStatVlanName
	}
	::= { sysVlanxStatTable 1 } 

SysVlanxStatEntry ::= 
	SEQUENCE {
        	sysVlanxStatVlanName                                   LongDisplayString,
        	sysVlanxStatInMulticastPkts                            Counter64,
        	sysVlanxStatInBroadcastPkts                            Counter64,
        	sysVlanxStatOutMulticastPkts                           Counter64,
        	sysVlanxStatOutBroadcastPkts                           Counter64,
        	sysVlanxStatHcInOctets                                 Counter64,
        	sysVlanxStatHcInUcastPkts                              Counter64,
        	sysVlanxStatHcInMulticastPkts                          Counter64,
        	sysVlanxStatHcInBroadcastPkts                          Counter64,
        	sysVlanxStatHcOutOctets                                Counter64,
        	sysVlanxStatHcOutUcastPkts                             Counter64,
        	sysVlanxStatHcOutMulticastPkts                         Counter64,
        	sysVlanxStatHcOutBroadcastPkts                         Counter64,
        	sysVlanxStatHighSpeed                                  Counter64,
        	sysVlanxStatConnectorPresent                           Integer32,
        	sysVlanxStatCounterDiscontinuityTime                   Counter64
	}

sysVlanxStatVlanName OBJECT-TYPE 
	SYNTAX LongDisplayString
	MAX-ACCESS read-only
	STATUS current
	DESCRIPTION
		"The name of a VLAN."
	::= { sysVlanxStatEntry 1 } 

sysVlanxStatInMulticastPkts OBJECT-TYPE 
	SYNTAX Counter64
	MAX-ACCESS read-only
	STATUS current
	DESCRIPTION
		"The number of packets, delivered by this sub-layer to a
		higher (sub-)layer, which were addressed to a multicast
		address at this sub-layer.  For a MAC layer protocol, this
		includes both Group and Functional addresses."
	::= { sysVlanxStatEntry 2 } 

sysVlanxStatInBroadcastPkts OBJECT-TYPE 
	SYNTAX Counter64
	MAX-ACCESS read-only
	STATUS current
	DESCRIPTION
		"The number of packets, delivered by this sub-layer to a
		higher (sub-)layer, which were addressed to a broadcast
		address at this sub-layer."
	::= { sysVlanxStatEntry 3 } 

sysVlanxStatOutMulticastPkts OBJECT-TYPE 
	SYNTAX Counter64
	MAX-ACCESS read-only
	STATUS current
	DESCRIPTION
		"The total number of packets that higher-level protocols
		requested be transmitted, and which were addressed to a
		multicast address at this sub-layer, including those that
		were discarded or not sent.  For a MAC layer protocol, this
		includes both Group and Functional addresses."
	::= { sysVlanxStatEntry 4 } 

sysVlanxStatOutBroadcastPkts OBJECT-TYPE 
	SYNTAX Counter64
	MAX-ACCESS read-only
	STATUS current
	DESCRIPTION
		"The total number of packets that higher-level protocols
		requested be transmitted, and which were addressed to a
		broadcast address at this sub-layer, including those that
		were discarded or not sent."
	::= { sysVlanxStatEntry 5 } 

sysVlanxStatHcInOctets OBJECT-TYPE 
	SYNTAX Counter64
	MAX-ACCESS read-only
	STATUS current
	DESCRIPTION
		"The total number of octets received on the interface,
		including framing characters."
	::= { sysVlanxStatEntry 6 } 

sysVlanxStatHcInUcastPkts OBJECT-TYPE 
	SYNTAX Counter64
	MAX-ACCESS read-only
	STATUS current
	DESCRIPTION
		"The number of packets, delivered by this sub-layer to a
		higher (sub-)layer, which were not addressed to a multicast
		or broadcast address at this sub-layer."
	::= { sysVlanxStatEntry 7 } 

sysVlanxStatHcInMulticastPkts OBJECT-TYPE 
	SYNTAX Counter64
	MAX-ACCESS read-only
	STATUS current
	DESCRIPTION
		"The number of packets, delivered by this sub-layer to a
		higher (sub-)layer, which were addressed to a multicast
		address at this sub-layer.  For a MAC layer protocol, this
		includes both Group and Functional addresses."
	::= { sysVlanxStatEntry 8 } 

sysVlanxStatHcInBroadcastPkts OBJECT-TYPE 
	SYNTAX Counter64
	MAX-ACCESS read-only
	STATUS current
	DESCRIPTION
		"The number of packets, delivered by this sub-layer to a
		higher (sub-)layer, which were addressed to a broadcast
		address at this sub-layer."
	::= { sysVlanxStatEntry 9 } 

sysVlanxStatHcOutOctets OBJECT-TYPE 
	SYNTAX Counter64
	MAX-ACCESS read-only
	STATUS current
	DESCRIPTION
		"The total number of octets transmitted out of the
		interface, including framing characters."
	::= { sysVlanxStatEntry 10 } 

sysVlanxStatHcOutUcastPkts OBJECT-TYPE 
	SYNTAX Counter64
	MAX-ACCESS read-only
	STATUS current
	DESCRIPTION
		"The total number of packets that higher-level protocols
		requested be transmitted, and which were not addressed to a
		multicast or broadcast address at this sub-layer, including
		those that were discarded or not sent."
	::= { sysVlanxStatEntry 11 } 

sysVlanxStatHcOutMulticastPkts OBJECT-TYPE 
	SYNTAX Counter64
	MAX-ACCESS read-only
	STATUS current
	DESCRIPTION
		"The total number of packets that higher-level protocols
		requested be transmitted, and which were addressed to a
		multicast address at this sub-layer, including those that
		were discarded or not sent.  For a MAC layer protocol, this
		includes both Group and Functional addresses."
	::= { sysVlanxStatEntry 12 } 

sysVlanxStatHcOutBroadcastPkts OBJECT-TYPE 
	SYNTAX Counter64
	MAX-ACCESS read-only
	STATUS current
	DESCRIPTION
		"The total number of packets that higher-level protocols
		requested be transmitted, and which were addressed to a
		broadcast address at this sub-layer, including those that
		were discarded or not sent."
	::= { sysVlanxStatEntry 13 } 

sysVlanxStatHighSpeed OBJECT-TYPE 
	SYNTAX Counter64
	MAX-ACCESS read-only
	STATUS current
	DESCRIPTION
		"An estimate of the interface's current bandwidth in units
		of 1,000,000 bits per second.  If this object reports a
		value of `n' then the speed of the interface is somewhere in
		the range of `n-500,000' to `n+499,999'.  For interfaces
		which do not vary in bandwidth or for those where no
		accurate estimation can be made, this object should contain
		the nominal bandwidth.  For a sub-layer which has no concept
		of bandwidth, this object should be zero."
	::= { sysVlanxStatEntry 14 } 

sysVlanxStatConnectorPresent OBJECT-TYPE 
	SYNTAX Integer32
	MAX-ACCESS read-only
	STATUS current
	DESCRIPTION
		"This object has the value 'true(1)' if the interface
		sublayer has a physical connector and the value 'false(2)'
		otherwise."
	::= { sysVlanxStatEntry 15 } 

sysVlanxStatCounterDiscontinuityTime OBJECT-TYPE 
	SYNTAX Counter64
	MAX-ACCESS read-only
	STATUS current
	DESCRIPTION
		"The value of sysUpTime on the most recent occasion at which
		any one or more of this interface's counters suffered a
		discontinuity.  The relevant counters are the specific
		instances associated with this interface of any Counter32 or
		Counter64 object contained in the sysInterfaceTable or sysInterfaceXTable. 
		If no such discontinuities have occurred since the last re-
		initialization of the local management subsystem, then this
		object contains a zero value."
	::= { sysVlanxStatEntry 16 } 

--==================================================================
-- Vcmp
--==================================================================
sysVcmpNumber OBJECT-TYPE 
	SYNTAX INTEGER
	MAX-ACCESS read-only
	STATUS current
	DESCRIPTION
		"The number of sysVcmp entries in the table."
	::= { sysVcmp 1 } 

sysVcmpTable OBJECT-TYPE
	SYNTAX SEQUENCE OF SysVcmpEntry
	MAX-ACCESS not-accessible
	STATUS current
	DESCRIPTION
		"A list VCMP guest configurations."
	::= { sysVcmp 2 } 

sysVcmpEntry OBJECT-TYPE
	SYNTAX  SysVcmpEntry
	MAX-ACCESS not-accessible
	STATUS current
	DESCRIPTION
		"Columns in the sysVcmp Table"
	INDEX {
		sysVcmpVcmpName
	}
	::= { sysVcmpTable 1 } 

SysVcmpEntry ::= 
	SEQUENCE {
        	sysVcmpVcmpName                                        LongDisplayString,
        	sysVcmpHostname                                        LongDisplayString,
        	sysVcmpSlots                                           INTEGER,
        	sysVcmpState                                           INTEGER,
        	sysVcmpMgmtNetwork                                     INTEGER,
        	sysVcmpMgmtAddrType                                    InetAddressType,
        	sysVcmpMgmtAddr                                        InetAddress,
        	sysVcmpMgmtNetmaskType                                 InetAddressType,
        	sysVcmpMgmtNetmask                                     InetAddress,
        	sysVcmpMgmtGwType                                      InetAddressType,
        	sysVcmpMgmtGw                                          InetAddress,
        	sysVcmpVcmpId                                          INTEGER,
        	sysVcmpMgmtBaseMac                                     MacAddress,
        	sysVcmpBaseMac                                         MacAddress,
        	sysVcmpMacPoolSize                                     INTEGER,
        	sysVcmpInitialImage                                    LongDisplayString,
        	sysVcmpVirtualDisk                                     LongDisplayString,
        	sysVcmpInitialHotfix                                   LongDisplayString,
        	sysVcmpMinSlots                                        INTEGER,
        	sysVcmpCoresPerSlot                                    INTEGER
	}

sysVcmpVcmpName OBJECT-TYPE 
	SYNTAX LongDisplayString
	MAX-ACCESS read-only
	STATUS current
	DESCRIPTION
		"The name of the VCMP guest."
	::= { sysVcmpEntry 1 } 

sysVcmpHostname OBJECT-TYPE 
	SYNTAX LongDisplayString
	MAX-ACCESS read-only
	STATUS current
	DESCRIPTION
		"The host name of the VCMP guest."
	::= { sysVcmpEntry 2 } 

sysVcmpSlots OBJECT-TYPE 
	SYNTAX INTEGER
	MAX-ACCESS read-only
	STATUS current
	DESCRIPTION
		"The maximum number of slots to which the VCMP guest may be
	         allocated."
	::= { sysVcmpEntry 3 } 

sysVcmpState OBJECT-TYPE 
	SYNTAX INTEGER {
		configured(0),
		provisioned(1),
		deployed(2)
	}
	MAX-ACCESS read-only
	STATUS current
	DESCRIPTION
		"VCMP guests can be in one of three user-chosen states: Configured,
		 Provisioned, or Deployed. 
		 A guest in the Configured state has no hardware resources allocated 
		  to it and has no virtual machines running. 
		 A guest in the Provisioned state has hardware resources allocated 
		  but no virtual machines running. 
		 A guest in the Deployed has hardware resources and should have 
		  virtual machines running. 
		 The vcmpd daemon tries to launch and maintain any virtual machines 
		  that belong to VCMP guests in the Deployed state."
	::= { sysVcmpEntry 4 } 

sysVcmpMgmtNetwork OBJECT-TYPE 
	SYNTAX INTEGER {
		bridged(0),
		isolated(1)
	}
	MAX-ACCESS read-only
	STATUS current
	DESCRIPTION
		"A VCMP guest is set to one of two management network modes: bridged or
		 isolated. In bridged mode, the management interface of the guest's 
		 virtual machines are attached to the management network of the hypervisor. 
		 This allows remote access over the virtual machines' management interfaces.
		 In isolated mode, the virtual machines' management interfaces are NOT 
		 connected to the hypervisor's management network. Console access or SSH 
		 access over the guest's VLANs is required to administer the guest's 
		 virtual machines."
	::= { sysVcmpEntry 5 } 

sysVcmpMgmtAddrType OBJECT-TYPE 
	SYNTAX InetAddressType
	MAX-ACCESS read-only
	STATUS current
	DESCRIPTION
		"The IP address type of sysMgmtAddr."
	::= { sysVcmpEntry 6 } 

sysVcmpMgmtAddr OBJECT-TYPE 
	SYNTAX InetAddress
	MAX-ACCESS read-only
	STATUS current
	DESCRIPTION
		"The IP address of the management port of a VCMP guest. It is interpreted 
		 within the context of a sysMgmtAddrType value."
	::= { sysVcmpEntry 7 } 

sysVcmpMgmtNetmaskType OBJECT-TYPE 
	SYNTAX InetAddressType
	MAX-ACCESS read-only
	STATUS current
	DESCRIPTION
		"The IP address type of sysMgmtNetmask."
	::= { sysVcmpEntry 8 } 

sysVcmpMgmtNetmask OBJECT-TYPE 
	SYNTAX InetAddress
	MAX-ACCESS read-only
	STATUS current
	DESCRIPTION
		"The netmask of the management port of a VCMP guest. It is interpreted 
		 within the context of a sysMgmtNetmaskType value."
	::= { sysVcmpEntry 9 } 

sysVcmpMgmtGwType OBJECT-TYPE 
	SYNTAX InetAddressType
	MAX-ACCESS read-only
	STATUS current
	DESCRIPTION
		"The IP address type of sysMgmtGw."
	::= { sysVcmpEntry 10 } 

sysVcmpMgmtGw OBJECT-TYPE 
	SYNTAX InetAddress
	MAX-ACCESS read-only
	STATUS current
	DESCRIPTION
		"The gateway of the management port of VCMP guest. It is interpreted 
		 within the context of a sysMgmtGwType value."
	::= { sysVcmpEntry 11 } 

sysVcmpVcmpId OBJECT-TYPE 
	SYNTAX INTEGER
	MAX-ACCESS read-only
	STATUS current
	DESCRIPTION
		"VCMP guest ID (valid range is 1-65535)."
	::= { sysVcmpEntry 12 } 

sysVcmpMgmtBaseMac OBJECT-TYPE 
	SYNTAX MacAddress
	MAX-ACCESS read-only
	STATUS current
	DESCRIPTION
		"The base MAC address of the management port of this VCMP guest."
	::= { sysVcmpEntry 13 } 

sysVcmpBaseMac OBJECT-TYPE 
	SYNTAX MacAddress
	MAX-ACCESS read-only
	STATUS current
	DESCRIPTION
		"The base MAC address assigned to this VCMP guest."
	::= { sysVcmpEntry 14 } 

sysVcmpMacPoolSize OBJECT-TYPE 
	SYNTAX INTEGER
	MAX-ACCESS read-only
	STATUS current
	DESCRIPTION
		"The number of MAC addresses assigned to this VCMP guest."
	::= { sysVcmpEntry 15 } 

sysVcmpInitialImage OBJECT-TYPE 
	SYNTAX LongDisplayString
	MAX-ACCESS read-only
	STATUS current
	DESCRIPTION
		"The initial software image file name that the hypervisor should use when 
		 installing TMOS to a guest's virtual disks. This does not reflect 
		 changes made in the Guest."
	::= { sysVcmpEntry 16 } 

sysVcmpVirtualDisk OBJECT-TYPE 
	SYNTAX LongDisplayString
	MAX-ACCESS read-only
	STATUS current
	DESCRIPTION
		"The virtual disk that the VCMP guest is using."
	::= { sysVcmpEntry 17 } 

sysVcmpInitialHotfix OBJECT-TYPE 
	SYNTAX LongDisplayString
	MAX-ACCESS read-only
	STATUS current
	DESCRIPTION
		"The initial software hotfix image file name that the hypervisor should
	         use when installing TMOS to a guest's virtual disks. This does not
	         reflect changes made in the Guest."
	::= { sysVcmpEntry 18 } 

sysVcmpMinSlots OBJECT-TYPE 
	SYNTAX INTEGER
	MAX-ACCESS read-only
	STATUS current
	DESCRIPTION
		"The minimum number of slots to which the VCMP guest may be
	         allocated."
	::= { sysVcmpEntry 19 } 

sysVcmpCoresPerSlot OBJECT-TYPE 
	SYNTAX INTEGER
	MAX-ACCESS read-only
	STATUS current
	DESCRIPTION
		"The number of cores per slot that should be allocated to the
	         VCMP guest."
	::= { sysVcmpEntry 20 } 

--==================================================================
-- Vcmp_cpu_core
--==================================================================
sysVcmpCpuCoreNumber OBJECT-TYPE 
	SYNTAX INTEGER
	MAX-ACCESS read-only
	STATUS current
	DESCRIPTION
		"The number of sysVcmpCpuCore entries in the table."
	::= { sysVcmpCpuCore 1 } 

sysVcmpCpuCoreTable OBJECT-TYPE
	SYNTAX SEQUENCE OF SysVcmpCpuCoreEntry
	MAX-ACCESS not-accessible
	STATUS current
	DESCRIPTION
		"A list of CPU cores assigned to VCMP guest."
	::= { sysVcmpCpuCore 2 } 

sysVcmpCpuCoreEntry OBJECT-TYPE
	SYNTAX  SysVcmpCpuCoreEntry
	MAX-ACCESS not-accessible
	STATUS current
	DESCRIPTION
		"Columns in the sysVcmpCpuCore Table"
	INDEX {
		sysVcmpCpuCoreVcmpName,
		sysVcmpCpuCoreCpuCoreId
	}
	::= { sysVcmpCpuCoreTable 1 } 

SysVcmpCpuCoreEntry ::= 
	SEQUENCE {
        	sysVcmpCpuCoreVcmpName                                 LongDisplayString,
        	sysVcmpCpuCoreCpuCoreId                                LongDisplayString
	}

sysVcmpCpuCoreVcmpName OBJECT-TYPE 
	SYNTAX LongDisplayString
	MAX-ACCESS read-only
	STATUS current
	DESCRIPTION
		"The VCMP guest name."
	::= { sysVcmpCpuCoreEntry 1 } 

sysVcmpCpuCoreCpuCoreId OBJECT-TYPE 
	SYNTAX LongDisplayString
	MAX-ACCESS read-only
	STATUS current
	DESCRIPTION
		"CPU cores assigned to VCMP guest.
		NOTE: cpu_core_id does not need to refer to existing objects in
		the cpu_core table. This can happen if a pulled blade causes 
		cores that were assigned to a VCMP object to no longer exist."
	::= { sysVcmpCpuCoreEntry 2 } 

--==================================================================
-- Vcmp_vlan
--==================================================================
sysVcmpVlanNumber OBJECT-TYPE 
	SYNTAX INTEGER
	MAX-ACCESS read-only
	STATUS current
	DESCRIPTION
		"The number of sysVcmpVlan entries in the table."
	::= { sysVcmpVlan 1 } 

sysVcmpVlanTable OBJECT-TYPE
	SYNTAX SEQUENCE OF SysVcmpVlanEntry
	MAX-ACCESS not-accessible
	STATUS current
	DESCRIPTION
		"A list of VLANs associated with the VCMP guest."
	::= { sysVcmpVlan 2 } 

sysVcmpVlanEntry OBJECT-TYPE
	SYNTAX  SysVcmpVlanEntry
	MAX-ACCESS not-accessible
	STATUS current
	DESCRIPTION
		"Columns in the sysVcmpVlan Table"
	INDEX {
		sysVcmpVlanVcmpName,
		sysVcmpVlanVlanName
	}
	::= { sysVcmpVlanTable 1 } 

SysVcmpVlanEntry ::= 
	SEQUENCE {
        	sysVcmpVlanVcmpName                                    LongDisplayString,
        	sysVcmpVlanVlanName                                    LongDisplayString
	}

sysVcmpVlanVcmpName OBJECT-TYPE 
	SYNTAX LongDisplayString
	MAX-ACCESS read-only
	STATUS current
	DESCRIPTION
		"VCMP guest name"
	::= { sysVcmpVlanEntry 1 } 

sysVcmpVlanVlanName OBJECT-TYPE 
	SYNTAX LongDisplayString
	MAX-ACCESS read-only
	STATUS current
	DESCRIPTION
		"The name of the VLAN assigned to a VCMP guest."
	::= { sysVcmpVlanEntry 2 } 

--==================================================================
-- Vcmp_stat
--==================================================================
sysVcmpStatNumber OBJECT-TYPE 
	SYNTAX INTEGER
	MAX-ACCESS read-only
	STATUS current
	DESCRIPTION
		"The number of sysVcmpStat entries in the table."
	::= { sysVcmpStat 1 } 

sysVcmpStatTable OBJECT-TYPE
	SYNTAX SEQUENCE OF SysVcmpStatEntry
	MAX-ACCESS not-accessible
	STATUS current
	DESCRIPTION
		"The statistics and state of this VCMP guest."
	::= { sysVcmpStat 2 } 

sysVcmpStatEntry OBJECT-TYPE
	SYNTAX  SysVcmpStatEntry
	MAX-ACCESS not-accessible
	STATUS current
	DESCRIPTION
		"Columns in the sysVcmpStat Table"
	INDEX {
		sysVcmpStatVcmpName,
		sysVcmpStatSlotId
	}
	::= { sysVcmpStatTable 1 } 

SysVcmpStatEntry ::= 
	SEQUENCE {
        	sysVcmpStatVcmpName                                    LongDisplayString,
        	sysVcmpStatVcmpId                                      INTEGER,
        	sysVcmpStatSlotId                                      INTEGER,
        	sysVcmpStatVmStatus                                    INTEGER,
        	sysVcmpStatDiskUse                                     CounterBasedGauge64,
        	sysVcmpStatMemoryUse                                   CounterBasedGauge64,
        	sysVcmpStatBaseMac                                     LongDisplayString,
        	sysVcmpStatMacPoolSize                                 INTEGER,
        	sysVcmpStatCores                                       INTEGER,
        	sysVcmpStatVdisk                                       LongDisplayString,
        	sysVcmpStatStarts                                      INTEGER,
        	sysVcmpStatRetries                                     INTEGER,
        	sysVcmpStatUptime                                      Counter64,
        	sysVcmpStatComment                                     LongDisplayString,
        	sysVcmpStatInterfaceNames                              LongDisplayString,
        	sysVcmpStatCoreNames                                   LongDisplayString,
        	sysVcmpStatPrompt                                      LongDisplayString,
        	sysVcmpStatCpuUsageRecent                              Gauge,
        	sysVcmpStatCpuUsage1min                                Gauge,
        	sysVcmpStatCpuUsage5mins                               Gauge,
        	sysVcmpStatPktsIn                                      Counter64,
        	sysVcmpStatBytesIn                                     Counter64,
        	sysVcmpStatMcastIn                                     Counter64,
        	sysVcmpStatDropsIn                                     Counter64,
        	sysVcmpStatPktsOut                                     Counter64,
        	sysVcmpStatBytesOut                                    Counter64,
        	sysVcmpStatMcastOut                                    Counter64,
        	sysVcmpStatDropsOut                                    Counter64
	}

sysVcmpStatVcmpName OBJECT-TYPE 
	SYNTAX LongDisplayString
	MAX-ACCESS read-only
	STATUS current
	DESCRIPTION
		"The name of the VCMP guest."
	::= { sysVcmpStatEntry 1 } 

sysVcmpStatVcmpId OBJECT-TYPE 
	SYNTAX INTEGER
	MAX-ACCESS read-only
	STATUS current
	DESCRIPTION
		"The VCMP guest ID (valid range is 1 to 65535)."
	::= { sysVcmpStatEntry 2 } 

sysVcmpStatSlotId OBJECT-TYPE 
	SYNTAX INTEGER(1..2147483647)
	MAX-ACCESS read-only
	STATUS current
	DESCRIPTION
		"The ID of the slot on which the VCMP guest resides."
	::= { sysVcmpStatEntry 3 } 

sysVcmpStatVmStatus OBJECT-TYPE 
	SYNTAX INTEGER {
		unknown(0),
		created(1),
		stopped(2),
		starting(3),
		running(4),
		stopping(5),
		installing-vdisk(6),
		deleted(7),
		failed(8),
		inactive(9),
		acquiring-vdisk(10),
		waiting-install(11),
		waiting-migrate(12),
		migrating-vdisk(13),
		waiting-start(14),
		waiting-create(15)
	}
	MAX-ACCESS read-only
	STATUS current
	DESCRIPTION
		"The status of this VCMP guest."
	::= { sysVcmpStatEntry 4 } 

sysVcmpStatDiskUse OBJECT-TYPE 
	SYNTAX CounterBasedGauge64
	MAX-ACCESS read-only
	STATUS current
	DESCRIPTION
		"The disk space used by this VCMP guest (in bytes)."
	::= { sysVcmpStatEntry 5 } 

sysVcmpStatMemoryUse OBJECT-TYPE 
	SYNTAX CounterBasedGauge64
	MAX-ACCESS read-only
	STATUS current
	DESCRIPTION
		"The memory space allocated by this VCMP guest (in bytes)."
	::= { sysVcmpStatEntry 6 } 

sysVcmpStatBaseMac OBJECT-TYPE 
	SYNTAX LongDisplayString
	MAX-ACCESS read-only
	STATUS current
	DESCRIPTION
		"The base MAC address assigned to this VCMP guest."
	::= { sysVcmpStatEntry 7 } 

sysVcmpStatMacPoolSize OBJECT-TYPE 
	SYNTAX INTEGER
	MAX-ACCESS read-only
	STATUS current
	DESCRIPTION
		"The number of MAC addresses assigned to this VCMP guest."
	::= { sysVcmpStatEntry 8 } 

sysVcmpStatCores OBJECT-TYPE 
	SYNTAX INTEGER
	MAX-ACCESS read-only
	STATUS current
	DESCRIPTION
		"The number of cores assigned to this VCMP guest on this slot."
	::= { sysVcmpStatEntry 9 } 

sysVcmpStatVdisk OBJECT-TYPE 
	SYNTAX LongDisplayString
	MAX-ACCESS read-only
	STATUS current
	DESCRIPTION
		"The virtual disk assigned to this VCMP guest."
	::= { sysVcmpStatEntry 10 } 

sysVcmpStatStarts OBJECT-TYPE 
	SYNTAX INTEGER
	MAX-ACCESS read-only
	STATUS current
	DESCRIPTION
		"The number of starts of this VCMP guest."
	::= { sysVcmpStatEntry 11 } 

sysVcmpStatRetries OBJECT-TYPE 
	SYNTAX INTEGER
	MAX-ACCESS read-only
	STATUS current
	DESCRIPTION
		"The number of retries of this VCMP guest."
	::= { sysVcmpStatEntry 12 } 

sysVcmpStatUptime OBJECT-TYPE 
	SYNTAX Counter64
	MAX-ACCESS read-only
	STATUS current
	DESCRIPTION
		"The time at which this VCMP guest became up and running."
	::= { sysVcmpStatEntry 13 } 

sysVcmpStatComment OBJECT-TYPE 
	SYNTAX LongDisplayString
	MAX-ACCESS read-only
	STATUS current
	DESCRIPTION
		"The error or state messages for this VCMP guest."
	::= { sysVcmpStatEntry 14 } 

sysVcmpStatInterfaceNames OBJECT-TYPE 
	SYNTAX LongDisplayString
	MAX-ACCESS read-only
	STATUS current
	DESCRIPTION
		"The interfaces assigned to this VCMP guest."
	::= { sysVcmpStatEntry 15 } 

sysVcmpStatCoreNames OBJECT-TYPE 
	SYNTAX LongDisplayString
	MAX-ACCESS read-only
	STATUS current
	DESCRIPTION
		"The cores assigned to this VCMP guest."
	::= { sysVcmpStatEntry 16 } 

sysVcmpStatPrompt OBJECT-TYPE 
	SYNTAX LongDisplayString
	MAX-ACCESS read-only
	STATUS current
	DESCRIPTION
		"The prompt status of this VCMP guest."
	::= { sysVcmpStatEntry 17 } 

sysVcmpStatCpuUsageRecent OBJECT-TYPE 
	SYNTAX Gauge
	MAX-ACCESS read-only
	STATUS current
	DESCRIPTION
		"Recent CPU usage for this VCMP guest."
	::= { sysVcmpStatEntry 18 } 

sysVcmpStatCpuUsage1min OBJECT-TYPE 
	SYNTAX Gauge
	MAX-ACCESS read-only
	STATUS current
	DESCRIPTION
		"CPU usage in the past minute for this VCMP guest."
	::= { sysVcmpStatEntry 19 } 

sysVcmpStatCpuUsage5mins OBJECT-TYPE 
	SYNTAX Gauge
	MAX-ACCESS read-only
	STATUS current
	DESCRIPTION
		"CPU usage in the past 5 minutes for this VCMP guest."
	::= { sysVcmpStatEntry 20 } 

sysVcmpStatPktsIn OBJECT-TYPE 
	SYNTAX Counter64
	MAX-ACCESS read-only
	STATUS current
	DESCRIPTION
		"Incoming packet count for this VCMP guest."
	::= { sysVcmpStatEntry 21 } 

sysVcmpStatBytesIn OBJECT-TYPE 
	SYNTAX Counter64
	MAX-ACCESS read-only
	STATUS current
	DESCRIPTION
		"Incoming byte count for this VCMP guest."
	::= { sysVcmpStatEntry 22 } 

sysVcmpStatMcastIn OBJECT-TYPE 
	SYNTAX Counter64
	MAX-ACCESS read-only
	STATUS current
	DESCRIPTION
		"Incoming multicasts for this VCMP guest."
	::= { sysVcmpStatEntry 23 } 

sysVcmpStatDropsIn OBJECT-TYPE 
	SYNTAX Counter64
	MAX-ACCESS read-only
	STATUS current
	DESCRIPTION
		"Drops on incoming traffic for this VCMP guest."
	::= { sysVcmpStatEntry 24 } 

sysVcmpStatPktsOut OBJECT-TYPE 
	SYNTAX Counter64
	MAX-ACCESS read-only
	STATUS current
	DESCRIPTION
		"Outgoing packet count for this VCMP guest."
	::= { sysVcmpStatEntry 25 } 

sysVcmpStatBytesOut OBJECT-TYPE 
	SYNTAX Counter64
	MAX-ACCESS read-only
	STATUS current
	DESCRIPTION
		"Outgoing byte count for this VCMP guest."
	::= { sysVcmpStatEntry 26 } 

sysVcmpStatMcastOut OBJECT-TYPE 
	SYNTAX Counter64
	MAX-ACCESS read-only
	STATUS current
	DESCRIPTION
		"Outgoing multicasts for this VCMP guest."
	::= { sysVcmpStatEntry 27 } 

sysVcmpStatDropsOut OBJECT-TYPE 
	SYNTAX Counter64
	MAX-ACCESS read-only
	STATUS current
	DESCRIPTION
		"Drops on outgoing traffic for this VCMP guest."
	::= { sysVcmpStatEntry 28 } 

--==================================================================
-- Chassis_slot
--==================================================================
sysChassisSlotNumber OBJECT-TYPE 
	SYNTAX INTEGER
	MAX-ACCESS read-only
	STATUS current
	DESCRIPTION
		"The number of sysChassisSlot entries in the table."
	::= { sysChassisSlot 1 } 

sysChassisSlotTable OBJECT-TYPE
	SYNTAX SEQUENCE OF SysChassisSlotEntry
	MAX-ACCESS not-accessible
	STATUS current
	DESCRIPTION
		"A table containing slot information in the chassis."
	::= { sysChassisSlot 2 } 

sysChassisSlotEntry OBJECT-TYPE
	SYNTAX  SysChassisSlotEntry
	MAX-ACCESS not-accessible
	STATUS current
	DESCRIPTION
		"Columns in the sysChassisSlot Table"
	INDEX {
		sysChassisSlotSlotId
	}
	::= { sysChassisSlotTable 1 } 

SysChassisSlotEntry ::= 
	SEQUENCE {
        	sysChassisSlotSlotId                                   INTEGER,
        	sysChassisSlotSerialNumber                             LongDisplayString,
        	sysChassisSlotDown                                     INTEGER,
        	sysChassisSlotState                                    INTEGER
	}

sysChassisSlotSlotId OBJECT-TYPE 
	SYNTAX INTEGER(1..2147483647)
	MAX-ACCESS read-only
	STATUS current
	DESCRIPTION
		"The slot id in the specified cluster."
	::= { sysChassisSlotEntry 1 } 

sysChassisSlotSerialNumber OBJECT-TYPE 
	SYNTAX LongDisplayString
	MAX-ACCESS read-only
	STATUS current
	DESCRIPTION
		"The serial number of this chassis slot."
	::= { sysChassisSlotEntry 2 } 

sysChassisSlotDown OBJECT-TYPE 
	SYNTAX INTEGER {
		false(0),
		true(1)
	}
	MAX-ACCESS read-only
	STATUS current
	DESCRIPTION
		"The state indicating whether the chassis slot is down or not."
	::= { sysChassisSlotEntry 3 } 

sysChassisSlotState OBJECT-TYPE 
	SYNTAX INTEGER {
		failed(0),
		unknown(1),
		empty(2),
		priming(3),
		ok(4)
	}
	MAX-ACCESS read-only
	STATUS current
	DESCRIPTION
		"The chassis slot state"
	::= { sysChassisSlotEntry 4 } 

--==================================================================
-- Sys_device
--==================================================================
sysSysDeviceNumber OBJECT-TYPE 
	SYNTAX INTEGER
	MAX-ACCESS read-only
	STATUS current
	DESCRIPTION
		"The number of sysSysDevice entries in the table."
	::= { sysSysDevice 1 } 

sysSysDeviceTable OBJECT-TYPE
	SYNTAX SEQUENCE OF SysSysDeviceEntry
	MAX-ACCESS not-accessible
	STATUS current
	DESCRIPTION
		"A table containing device information on devices connected to this machine"
	::= { sysSysDevice 2 } 

sysSysDeviceEntry OBJECT-TYPE
	SYNTAX  SysSysDeviceEntry
	MAX-ACCESS not-accessible
	STATUS current
	DESCRIPTION
		"Columns in the sysSysDevice Table"
	INDEX {
		sysSysDeviceName
	}
	::= { sysSysDeviceTable 1 } 

SysSysDeviceEntry ::= 
	SEQUENCE {
        	sysSysDeviceName                                       LongDisplayString,
        	sysSysDeviceMgmtIp                                     InetAddress,
        	sysSysDeviceMgmtIpType                                 InetAddressType,
        	sysSysDeviceHostname                                   LongDisplayString,
        	sysSysDeviceMirrorIp                                   InetAddress,
        	sysSysDeviceMirrorIpType                               InetAddressType,
        	sysSysDeviceMirrorSecondaryIp                          InetAddress,
        	sysSysDeviceMirrorSecondaryIpType                      InetAddressType,
        	sysSysDeviceMulticastInterface                         LongDisplayString,
        	sysSysDeviceMulticastAddr                              InetAddress,
        	sysSysDeviceMulticastAddrType                          InetAddressType,
        	sysSysDeviceMulticastPort                              InetPortNumber,
        	sysSysDeviceVersion                                    LongDisplayString,
        	sysSysDeviceProduct                                    LongDisplayString,
        	sysSysDeviceEdition                                    LongDisplayString,
        	sysSysDeviceMarketingName                              LongDisplayString,
        	sysSysDevicePlatformId                                 LongDisplayString,
        	sysSysDeviceChassisId                                  LongDisplayString
	}

sysSysDeviceName OBJECT-TYPE 
	SYNTAX LongDisplayString
	MAX-ACCESS read-only
	STATUS current
	DESCRIPTION
		"The unique device name"
	::= { sysSysDeviceEntry 1 } 

sysSysDeviceMgmtIp OBJECT-TYPE 
	SYNTAX InetAddress
	MAX-ACCESS read-only
	STATUS current
	DESCRIPTION
		"The ip used to connect to the device"
	::= { sysSysDeviceEntry 2 } 

sysSysDeviceMgmtIpType OBJECT-TYPE 
	SYNTAX InetAddressType
	MAX-ACCESS read-only
	STATUS current
	DESCRIPTION
		""
	::= { sysSysDeviceEntry 3 } 

sysSysDeviceHostname OBJECT-TYPE 
	SYNTAX LongDisplayString
	MAX-ACCESS read-only
	STATUS current
	DESCRIPTION
		"The hostname of the device"
	::= { sysSysDeviceEntry 4 } 

sysSysDeviceMirrorIp OBJECT-TYPE 
	SYNTAX InetAddress
	MAX-ACCESS read-only
	STATUS current
	DESCRIPTION
		"The mirror ip address"
	::= { sysSysDeviceEntry 5 } 

sysSysDeviceMirrorIpType OBJECT-TYPE 
	SYNTAX InetAddressType
	MAX-ACCESS read-only
	STATUS current
	DESCRIPTION
		""
	::= { sysSysDeviceEntry 6 } 

sysSysDeviceMirrorSecondaryIp OBJECT-TYPE 
	SYNTAX InetAddress
	MAX-ACCESS read-only
	STATUS current
	DESCRIPTION
		"The secondary mirror ip"
	::= { sysSysDeviceEntry 7 } 

sysSysDeviceMirrorSecondaryIpType OBJECT-TYPE 
	SYNTAX InetAddressType
	MAX-ACCESS read-only
	STATUS current
	DESCRIPTION
		""
	::= { sysSysDeviceEntry 8 } 

sysSysDeviceMulticastInterface OBJECT-TYPE 
	SYNTAX LongDisplayString
	MAX-ACCESS read-only
	STATUS current
	DESCRIPTION
		"Multicast Interface"
	::= { sysSysDeviceEntry 9 } 

sysSysDeviceMulticastAddr OBJECT-TYPE 
	SYNTAX InetAddress
	MAX-ACCESS read-only
	STATUS current
	DESCRIPTION
		"Multicast Address"
	::= { sysSysDeviceEntry 10 } 

sysSysDeviceMulticastAddrType OBJECT-TYPE 
	SYNTAX InetAddressType
	MAX-ACCESS read-only
	STATUS current
	DESCRIPTION
		""
	::= { sysSysDeviceEntry 11 } 

sysSysDeviceMulticastPort OBJECT-TYPE 
	SYNTAX InetPortNumber
	MAX-ACCESS read-only
	STATUS current
	DESCRIPTION
		"Multicast Port"
	::= { sysSysDeviceEntry 12 } 

sysSysDeviceVersion OBJECT-TYPE 
	SYNTAX LongDisplayString
	MAX-ACCESS read-only
	STATUS current
	DESCRIPTION
		"The product version"
	::= { sysSysDeviceEntry 13 } 

sysSysDeviceProduct OBJECT-TYPE 
	SYNTAX LongDisplayString
	MAX-ACCESS read-only
	STATUS current
	DESCRIPTION
		"The product installed on the device"
	::= { sysSysDeviceEntry 14 } 

sysSysDeviceEdition OBJECT-TYPE 
	SYNTAX LongDisplayString
	MAX-ACCESS read-only
	STATUS current
	DESCRIPTION
		"The edition of the product installed on the device"
	::= { sysSysDeviceEntry 15 } 

sysSysDeviceMarketingName OBJECT-TYPE 
	SYNTAX LongDisplayString
	MAX-ACCESS read-only
	STATUS current
	DESCRIPTION
		"The marketing name of the device"
	::= { sysSysDeviceEntry 16 } 

sysSysDevicePlatformId OBJECT-TYPE 
	SYNTAX LongDisplayString
	MAX-ACCESS read-only
	STATUS current
	DESCRIPTION
		"The platform name of the device"
	::= { sysSysDeviceEntry 17 } 

sysSysDeviceChassisId OBJECT-TYPE 
	SYNTAX LongDisplayString
	MAX-ACCESS read-only
	STATUS current
	DESCRIPTION
		"The unique chassis id of this device"
	::= { sysSysDeviceEntry 18 } 

--==================================================================
-- Unicast_addr
--==================================================================
sysUnicastAddrNumber OBJECT-TYPE 
	SYNTAX INTEGER
	MAX-ACCESS read-only
	STATUS current
	DESCRIPTION
		"The number of sysUnicastAddr entries in the table."
	::= { sysUnicastAddr 1 } 

sysUnicastAddrTable OBJECT-TYPE
	SYNTAX SEQUENCE OF SysUnicastAddrEntry
	MAX-ACCESS not-accessible
	STATUS current
	DESCRIPTION
		"A table that contains the unicast address/port combinations available on this device"
	::= { sysUnicastAddr 2 } 

sysUnicastAddrEntry OBJECT-TYPE
	SYNTAX  SysUnicastAddrEntry
	MAX-ACCESS not-accessible
	STATUS current
	DESCRIPTION
		"Columns in the sysUnicastAddr Table"
	INDEX {
		sysUnicastAddrName,
		sysUnicastAddrIndex
	}
	::= { sysUnicastAddrTable 1 } 

SysUnicastAddrEntry ::= 
	SEQUENCE {
        	sysUnicastAddrName                                     LongDisplayString,
        	sysUnicastAddrIndex                                    INTEGER,
        	sysUnicastAddrSourceIp                                 InetAddress,
        	sysUnicastAddrSourceIpType                             InetAddressType,
        	sysUnicastAddrSourcePort                               InetPortNumber
	}

sysUnicastAddrName OBJECT-TYPE 
	SYNTAX LongDisplayString
	MAX-ACCESS read-only
	STATUS current
	DESCRIPTION
		""
	::= { sysUnicastAddrEntry 1 } 

sysUnicastAddrIndex OBJECT-TYPE 
	SYNTAX INTEGER(1..2147483647)
	MAX-ACCESS read-only
	STATUS current
	DESCRIPTION
		"Index of the unicast addr within this table"
	::= { sysUnicastAddrEntry 2 } 

sysUnicastAddrSourceIp OBJECT-TYPE 
	SYNTAX InetAddress
	MAX-ACCESS read-only
	STATUS current
	DESCRIPTION
		"Source unicast address for this device"
	::= { sysUnicastAddrEntry 3 } 

sysUnicastAddrSourceIpType OBJECT-TYPE 
	SYNTAX InetAddressType
	MAX-ACCESS read-only
	STATUS current
	DESCRIPTION
		""
	::= { sysUnicastAddrEntry 4 } 

sysUnicastAddrSourcePort OBJECT-TYPE 
	SYNTAX InetPortNumber
	MAX-ACCESS read-only
	STATUS current
	DESCRIPTION
		"Source port for unicast on this device"
	::= { sysUnicastAddrEntry 5 } 

--==================================================================
-- Sys_device_active_modules
--==================================================================
sysSysDeviceActiveModulesNumber OBJECT-TYPE 
	SYNTAX INTEGER
	MAX-ACCESS read-only
	STATUS current
	DESCRIPTION
		"The number of sysSysDeviceActiveModules entries in the table."
	::= { sysSysDeviceActiveModules 1 } 

sysSysDeviceActiveModulesTable OBJECT-TYPE
	SYNTAX SEQUENCE OF SysSysDeviceActiveModulesEntry
	MAX-ACCESS not-accessible
	STATUS current
	DESCRIPTION
		"A table containing a list of the active modules on the device."
	::= { sysSysDeviceActiveModules 2 } 

sysSysDeviceActiveModulesEntry OBJECT-TYPE
	SYNTAX  SysSysDeviceActiveModulesEntry
	MAX-ACCESS not-accessible
	STATUS current
	DESCRIPTION
		"Columns in the sysSysDeviceActiveModules Table"
	INDEX {
		sysSysDeviceActiveModulesName,
		sysSysDeviceActiveModulesIndex
	}
	::= { sysSysDeviceActiveModulesTable 1 } 

SysSysDeviceActiveModulesEntry ::= 
	SEQUENCE {
        	sysSysDeviceActiveModulesName                          LongDisplayString,
        	sysSysDeviceActiveModulesIndex                         INTEGER,
        	sysSysDeviceActiveModulesModule                        LongDisplayString
	}

sysSysDeviceActiveModulesName OBJECT-TYPE 
	SYNTAX LongDisplayString
	MAX-ACCESS read-only
	STATUS current
	DESCRIPTION
		""
	::= { sysSysDeviceActiveModulesEntry 1 } 

sysSysDeviceActiveModulesIndex OBJECT-TYPE 
	SYNTAX INTEGER(1..2147483647)
	MAX-ACCESS read-only
	STATUS current
	DESCRIPTION
		"Index of the unicast addr within this table"
	::= { sysSysDeviceActiveModulesEntry 2 } 

sysSysDeviceActiveModulesModule OBJECT-TYPE 
	SYNTAX LongDisplayString
	MAX-ACCESS read-only
	STATUS current
	DESCRIPTION
		"An active module on the device"
	::= { sysSysDeviceActiveModulesEntry 3 } 

--==================================================================
-- Sys_device_inactive_modules
--==================================================================
sysSysDeviceInactiveModulesNumber OBJECT-TYPE 
	SYNTAX INTEGER
	MAX-ACCESS read-only
	STATUS current
	DESCRIPTION
		"The number of sysSysDeviceInactiveModules entries in the table."
	::= { sysSysDeviceInactiveModules 1 } 

sysSysDeviceInactiveModulesTable OBJECT-TYPE
	SYNTAX SEQUENCE OF SysSysDeviceInactiveModulesEntry
	MAX-ACCESS not-accessible
	STATUS current
	DESCRIPTION
		"A table containing a list of the inactive modules on the device."
	::= { sysSysDeviceInactiveModules 2 } 

sysSysDeviceInactiveModulesEntry OBJECT-TYPE
	SYNTAX  SysSysDeviceInactiveModulesEntry
	MAX-ACCESS not-accessible
	STATUS current
	DESCRIPTION
		"Columns in the sysSysDeviceInactiveModules Table"
	INDEX {
		sysSysDeviceInactiveModulesName,
		sysSysDeviceInactiveModulesIndex
	}
	::= { sysSysDeviceInactiveModulesTable 1 } 

SysSysDeviceInactiveModulesEntry ::= 
	SEQUENCE {
        	sysSysDeviceInactiveModulesName                        LongDisplayString,
        	sysSysDeviceInactiveModulesIndex                       INTEGER,
        	sysSysDeviceInactiveModulesModule                      LongDisplayString
	}

sysSysDeviceInactiveModulesName OBJECT-TYPE 
	SYNTAX LongDisplayString
	MAX-ACCESS read-only
	STATUS current
	DESCRIPTION
		""
	::= { sysSysDeviceInactiveModulesEntry 1 } 

sysSysDeviceInactiveModulesIndex OBJECT-TYPE 
	SYNTAX INTEGER(1..2147483647)
	MAX-ACCESS read-only
	STATUS current
	DESCRIPTION
		"Index of the unicast addr within this table"
	::= { sysSysDeviceInactiveModulesEntry 2 } 

sysSysDeviceInactiveModulesModule OBJECT-TYPE 
	SYNTAX LongDisplayString
	MAX-ACCESS read-only
	STATUS current
	DESCRIPTION
		"An inactive module on the device"
	::= { sysSysDeviceInactiveModulesEntry 3 } 

--==================================================================
-- Sys_device_optional_modules
--==================================================================
sysSysDeviceOptionalModulesNumber OBJECT-TYPE 
	SYNTAX INTEGER
	MAX-ACCESS read-only
	STATUS current
	DESCRIPTION
		"The number of sysSysDeviceOptionalModules entries in the table."
	::= { sysSysDeviceOptionalModules 1 } 

sysSysDeviceOptionalModulesTable OBJECT-TYPE
	SYNTAX SEQUENCE OF SysSysDeviceOptionalModulesEntry
	MAX-ACCESS not-accessible
	STATUS current
	DESCRIPTION
		"A table containing a list of the optional modules on the device."
	::= { sysSysDeviceOptionalModules 2 } 

sysSysDeviceOptionalModulesEntry OBJECT-TYPE
	SYNTAX  SysSysDeviceOptionalModulesEntry
	MAX-ACCESS not-accessible
	STATUS current
	DESCRIPTION
		"Columns in the sysSysDeviceOptionalModules Table"
	INDEX {
		sysSysDeviceOptionalModulesName,
		sysSysDeviceOptionalModulesIndex
	}
	::= { sysSysDeviceOptionalModulesTable 1 } 

SysSysDeviceOptionalModulesEntry ::= 
	SEQUENCE {
        	sysSysDeviceOptionalModulesName                        LongDisplayString,
        	sysSysDeviceOptionalModulesIndex                       INTEGER,
        	sysSysDeviceOptionalModulesModule                      LongDisplayString
	}

sysSysDeviceOptionalModulesName OBJECT-TYPE 
	SYNTAX LongDisplayString
	MAX-ACCESS read-only
	STATUS current
	DESCRIPTION
		""
	::= { sysSysDeviceOptionalModulesEntry 1 } 

sysSysDeviceOptionalModulesIndex OBJECT-TYPE 
	SYNTAX INTEGER(1..2147483647)
	MAX-ACCESS read-only
	STATUS current
	DESCRIPTION
		"Index of the unicast addr within this table"
	::= { sysSysDeviceOptionalModulesEntry 2 } 

sysSysDeviceOptionalModulesModule OBJECT-TYPE 
	SYNTAX LongDisplayString
	MAX-ACCESS read-only
	STATUS current
	DESCRIPTION
		"An optional module on the device"
	::= { sysSysDeviceOptionalModulesEntry 3 } 

--==================================================================
-- Sys_device_timelimited_modules
--==================================================================
sysSysDeviceTimelimitedModulesNumber OBJECT-TYPE 
	SYNTAX INTEGER
	MAX-ACCESS read-only
	STATUS current
	DESCRIPTION
		"The number of sysSysDeviceTimelimitedModules entries in the table."
	::= { sysSysDeviceTimelimitedModules 1 } 

sysSysDeviceTimelimitedModulesTable OBJECT-TYPE
	SYNTAX SEQUENCE OF SysSysDeviceTimelimitedModulesEntry
	MAX-ACCESS not-accessible
	STATUS current
	DESCRIPTION
		"A table containing a list of the timelimited modules on the device."
	::= { sysSysDeviceTimelimitedModules 2 } 

sysSysDeviceTimelimitedModulesEntry OBJECT-TYPE
	SYNTAX  SysSysDeviceTimelimitedModulesEntry
	MAX-ACCESS not-accessible
	STATUS current
	DESCRIPTION
		"Columns in the sysSysDeviceTimelimitedModules Table"
	INDEX {
		sysSysDeviceTimelimitedModulesName,
		sysSysDeviceTimelimitedModulesIndex
	}
	::= { sysSysDeviceTimelimitedModulesTable 1 } 

SysSysDeviceTimelimitedModulesEntry ::= 
	SEQUENCE {
        	sysSysDeviceTimelimitedModulesName                     LongDisplayString,
        	sysSysDeviceTimelimitedModulesIndex                    INTEGER,
        	sysSysDeviceTimelimitedModulesModule                   LongDisplayString
	}

sysSysDeviceTimelimitedModulesName OBJECT-TYPE 
	SYNTAX LongDisplayString
	MAX-ACCESS read-only
	STATUS current
	DESCRIPTION
		""
	::= { sysSysDeviceTimelimitedModulesEntry 1 } 

sysSysDeviceTimelimitedModulesIndex OBJECT-TYPE 
	SYNTAX INTEGER(1..2147483647)
	MAX-ACCESS read-only
	STATUS current
	DESCRIPTION
		"Index of the unicast addr within this table"
	::= { sysSysDeviceTimelimitedModulesEntry 2 } 

sysSysDeviceTimelimitedModulesModule OBJECT-TYPE 
	SYNTAX LongDisplayString
	MAX-ACCESS read-only
	STATUS current
	DESCRIPTION
		"An timelimited module on the device"
	::= { sysSysDeviceTimelimitedModulesEntry 3 } 

--==================================================================
-- Stp_globals2
--==================================================================
sysStpGlobals2Number OBJECT-TYPE 
	SYNTAX INTEGER
	MAX-ACCESS read-only
	STATUS current
	DESCRIPTION
		"The number of sysStpGlobals2 entries in the table."
	::= { sysStpGlobals2 1 } 

sysStpGlobals2Table OBJECT-TYPE
	SYNTAX SEQUENCE OF SysStpGlobals2Entry
	MAX-ACCESS not-accessible
	STATUS current
	DESCRIPTION
		"The STP domain's global information."
	::= { sysStpGlobals2 2 } 

sysStpGlobals2Entry OBJECT-TYPE
	SYNTAX  SysStpGlobals2Entry
	MAX-ACCESS not-accessible
	STATUS current
	DESCRIPTION
		"Columns in the sysStpGlobals2 Table"
	INDEX {
		sysStpGlobals2Name
	}
	::= { sysStpGlobals2Table 1 } 

SysStpGlobals2Entry ::= 
	SEQUENCE {
        	sysStpGlobals2Mode                                     INTEGER,
        	sysStpGlobals2FwdDelay                                 INTEGER,
        	sysStpGlobals2HelloTime                                INTEGER,
        	sysStpGlobals2MaxAge                                   INTEGER,
        	sysStpGlobals2TransmitHold                             INTEGER,
        	sysStpGlobals2MaxHops                                  INTEGER,
        	sysStpGlobals2Identifier                               LongDisplayString,
        	sysStpGlobals2Revision                                 INTEGER,
        	sysStpGlobals2Name                                     LongDisplayString
	}

sysStpGlobals2Mode OBJECT-TYPE 
	SYNTAX INTEGER {
		disable(0),
		stp(1),
		rstp(2),
		mstp(3),
		passthru(4)
	}
	MAX-ACCESS read-only
	STATUS current
	DESCRIPTION
		"The STP mode."
	::= { sysStpGlobals2Entry 1 } 

sysStpGlobals2FwdDelay OBJECT-TYPE 
	SYNTAX INTEGER
	MAX-ACCESS read-only
	STATUS current
	DESCRIPTION
		"The forward delay parameter, which controls how long an 
		interface was blocked from forwarding network traffic after 
		a reconfiguration of the spanning tree topology. The default 
		value is 15 seconds, and the valid range is 4-30 seconds.  
		Note that this parameter has no effect when the STP mode 
		is RSPT or MSTP, as long as all bridges in the spanning tree 
		use the RSTP or MSTP protocol."
	::= { sysStpGlobals2Entry 2 } 

sysStpGlobals2HelloTime OBJECT-TYPE 
	SYNTAX INTEGER
	MAX-ACCESS read-only
	STATUS current
	DESCRIPTION
		"The hello time, which is the time interval in seconds 
		between the periodic transmissions that communicate spanning 
		tree information to the adjacent bridges in the network. 
		The default value is 2 seconds, and the valid range is 1-10 seconds."
	::= { sysStpGlobals2Entry 3 } 

sysStpGlobals2MaxAge OBJECT-TYPE 
	SYNTAX INTEGER
	MAX-ACCESS read-only
	STATUS current
	DESCRIPTION
		"The maximum age parameter, which controls how long spanning tree 
		information received from other bridges is considered valid.  
		The default value is 20 seconds, and the valid range is 6-40 seconds."
	::= { sysStpGlobals2Entry 4 } 

sysStpGlobals2TransmitHold OBJECT-TYPE 
	SYNTAX INTEGER
	MAX-ACCESS read-only
	STATUS current
	DESCRIPTION
		"The transmit hold count parameter, which is an absolute limit on 
		the number of spanning tree protocol packets the BIG-IP may transmit 
		on a port in any hello time interval.  This ensures that the spanning 
		tree packets will not unduly load the network even in unstable 
		conditions. The default value is 6 packets, and the valid range 
		is 1-10 packets."
	::= { sysStpGlobals2Entry 5 } 

sysStpGlobals2MaxHops OBJECT-TYPE 
	SYNTAX INTEGER
	MAX-ACCESS read-only
	STATUS current
	DESCRIPTION
		"The maximum hops an MSTP packet may travel before it is discarded.  
		It's used only when the STP mode is MSTP."
	::= { sysStpGlobals2Entry 6 } 

sysStpGlobals2Identifier OBJECT-TYPE 
	SYNTAX LongDisplayString
	MAX-ACCESS read-only
	STATUS current
	DESCRIPTION
		"The configuration identifier name in a spanning tree region, 
		used to identify a group of adjacent bridges with identical 
		configuration name, configuration revision levels, and assignments 
		of VLANs to spanning tree instances.  This setting is used only 
		when the STP mode is MSTP."
	::= { sysStpGlobals2Entry 7 } 

sysStpGlobals2Revision OBJECT-TYPE 
	SYNTAX INTEGER
	MAX-ACCESS read-only
	STATUS current
	DESCRIPTION
		" The configuration revision level of the MSTP configuration.  
		It's used only when the STP mode is MSTP."
	::= { sysStpGlobals2Entry 8 } 

sysStpGlobals2Name OBJECT-TYPE 
	SYNTAX LongDisplayString
	MAX-ACCESS read-only
	STATUS current
	DESCRIPTION
		"The name this stp global configuration."
	::= { sysStpGlobals2Entry 9 } 

--==================================================================
-- Cpu_sensor_status_stat
--==================================================================
sysCpuSensorNumber OBJECT-TYPE 
	SYNTAX INTEGER
	MAX-ACCESS read-only
	STATUS current
	DESCRIPTION
		"The number of sysCpuSensor entries in the table."
	::= { sysCpuSensor 1 } 

sysCpuSensorTable OBJECT-TYPE
	SYNTAX SEQUENCE OF SysCpuSensorEntry
	MAX-ACCESS not-accessible
	STATUS current
	DESCRIPTION
		"A table containing information of CPU sensor status on the system."
	::= { sysCpuSensor 2 } 

sysCpuSensorEntry OBJECT-TYPE
	SYNTAX  SysCpuSensorEntry
	MAX-ACCESS not-accessible
	STATUS current
	DESCRIPTION
		"Columns in the sysCpuSensor Table"
	INDEX {
		sysCpuSensorSlot,
		sysCpuSensorIndex
	}
	::= { sysCpuSensorTable 1 } 

SysCpuSensorEntry ::= 
	SEQUENCE {
        	sysCpuSensorIndex                                      INTEGER,
        	sysCpuSensorTemperature                                INTEGER,
        	sysCpuSensorFanSpeed                                   Integer32,
        	sysCpuSensorName                                       LongDisplayString,
        	sysCpuSensorSlot                                       INTEGER
	}

sysCpuSensorIndex OBJECT-TYPE 
	SYNTAX INTEGER(1..2147483647)
	MAX-ACCESS read-only
	STATUS current
	DESCRIPTION
		"The CPU index on the system."
	::= { sysCpuSensorEntry 1 } 

sysCpuSensorTemperature OBJECT-TYPE 
	SYNTAX INTEGER
	MAX-ACCESS read-only
	STATUS current
	DESCRIPTION
		"The temperature of the indexed CPU on the system.
			This is only supported for the platform where
			the sensor data is available."
	::= { sysCpuSensorEntry 2 } 

sysCpuSensorFanSpeed OBJECT-TYPE 
	SYNTAX Integer32
	MAX-ACCESS read-only
	STATUS current
	DESCRIPTION
		"The fan speed (in RPM) of the indexed CPU on the system.,
			This is only supported for the platform where
			the sensor data is available."
	::= { sysCpuSensorEntry 3 } 

sysCpuSensorName OBJECT-TYPE 
	SYNTAX LongDisplayString
	MAX-ACCESS read-only
	STATUS current
	DESCRIPTION
		"Identifier for the CPU."
	::= { sysCpuSensorEntry 4 } 

sysCpuSensorSlot OBJECT-TYPE 
	SYNTAX INTEGER(1..2147483647)
	MAX-ACCESS read-only
	STATUS current
	DESCRIPTION
		"Chassis slot number, if applicable."
	::= { sysCpuSensorEntry 5 } 

--==================================================================
-- Cmi_sync_status
--==================================================================
sysCmSyncStatusId OBJECT-TYPE 
	SYNTAX INTEGER {
		unknown(0),
		syncing(1),
		needManualSync(2),
		inSync(3),
		syncFailed(4),
		syncDisconnected(5),
		standalone(6),
		awaitingInitialSync(7),
		incompatibleVersion(8),
		partialSync(9)
	}
	MAX-ACCESS read-only
	STATUS current
	DESCRIPTION
		"The sync status ID on the system.
		unknown - the device is disconnected from the device group;
		syncing - the device is joining the device group or has requested changes
		from device group or inconsistent with the group;
		needManualSync - changes have been made on the device not syncd to
		the device group;
		inSync - the device is consistent with the device group;
		syncFailed - the device is inconsistent with the device group, requires
		user intervention;
		syncDisconnected - the device is not connected to any peers; 
		standalone - the device is in a standalone configuration;
		awaitingInitialSync - the device is waiting for initial sync;
		incompatibleVersion - the device's version is incompatible with rest of
		the devices in the device group;
		partialSync - some but not all devices successfully received the last sync."
	::= { sysCmSyncStatus 1 } 

sysCmSyncStatusStatus OBJECT-TYPE 
	SYNTAX LongDisplayString
	MAX-ACCESS read-only
	STATUS current
	DESCRIPTION
		"The sync status on the system."
	::= { sysCmSyncStatus 2 } 

sysCmSyncStatusColor OBJECT-TYPE 
	SYNTAX INTEGER {
		green(0),
		yellow(1),
		red(2),
		blue(3),
		gray(4),
		black(5)
	}
	MAX-ACCESS read-only
	STATUS current
	DESCRIPTION
		"The color of the sync status on the system.
		green - the system is functioning correctly;
		yellow - the system may be functioning suboptimally;
		red - the system requires attention to function correctly;
		blue - the system's status is unknown or incomplete;
		gray - the system is intentionally not functioning (offline);
		black - the system is not connected to any peers."
	::= { sysCmSyncStatus 3 } 

sysCmSyncStatusSummary OBJECT-TYPE 
	SYNTAX LongDisplayString
	MAX-ACCESS read-only
	STATUS current
	DESCRIPTION
		"The summary of the sync status on the system."
	::= { sysCmSyncStatus 4 } 

--==================================================================
-- Cmi_sync_status_details
--==================================================================
sysCmSyncStatusDetailsNumber OBJECT-TYPE 
	SYNTAX INTEGER
	MAX-ACCESS read-only
	STATUS current
	DESCRIPTION
		"The number of sysCmSyncStatusDetails entries in the table."
	::= { sysCmSyncStatusDetails 1 } 

sysCmSyncStatusDetailsTable OBJECT-TYPE
	SYNTAX SEQUENCE OF SysCmSyncStatusDetailsEntry
	MAX-ACCESS not-accessible
	STATUS current
	DESCRIPTION
		"A table containing details of sync status on the system."
	::= { sysCmSyncStatusDetails 2 } 

sysCmSyncStatusDetailsEntry OBJECT-TYPE
	SYNTAX  SysCmSyncStatusDetailsEntry
	MAX-ACCESS not-accessible
	STATUS current
	DESCRIPTION
		"Columns in the sysCmSyncStatusDetails Table"
	INDEX {
		sysCmSyncStatusDetailsIndex
	}
	::= { sysCmSyncStatusDetailsTable 1 } 

SysCmSyncStatusDetailsEntry ::= 
	SEQUENCE {
        	sysCmSyncStatusDetailsIndex                            INTEGER,
        	sysCmSyncStatusDetailsDetails                          LongDisplayString
	}

sysCmSyncStatusDetailsIndex OBJECT-TYPE 
	SYNTAX INTEGER(1..2147483647)
	MAX-ACCESS read-only
	STATUS current
	DESCRIPTION
		"The index of the table that contains the details of the sync status
		on the system."
	::= { sysCmSyncStatusDetailsEntry 1 } 

sysCmSyncStatusDetailsDetails OBJECT-TYPE 
	SYNTAX LongDisplayString
	MAX-ACCESS read-only
	STATUS current
	DESCRIPTION
		"The details of the sync status on the system."
	::= { sysCmSyncStatusDetailsEntry 2 } 

--==================================================================
-- Cmi_failover_status
--==================================================================
sysCmFailoverStatusId OBJECT-TYPE 
	SYNTAX INTEGER {
		unknown(0),
		offline(1),
		forcedOffline(2),
		standby(3),
		active(4)
	}
	MAX-ACCESS read-only
	STATUS current
	DESCRIPTION
		"The failover status ID on the system.
		unknown - the failover status of the device is unknown;
		offline - the device is offline;
		forcedOffline - the device is forced offline;
		standby - the device is standby;
		active - the device  is active."
	::= { sysCmFailoverStatus 1 } 

sysCmFailoverStatusStatus OBJECT-TYPE 
	SYNTAX LongDisplayString
	MAX-ACCESS read-only
	STATUS current
	DESCRIPTION
		"The failover status on the system."
	::= { sysCmFailoverStatus 2 } 

sysCmFailoverStatusColor OBJECT-TYPE 
	SYNTAX INTEGER {
		green(0),
		yellow(1),
		red(2),
		blue(3),
		gray(4),
		black(5)
	}
	MAX-ACCESS read-only
	STATUS current
	DESCRIPTION
		"The color of the failover status on the system.
		green - the system is functioning correctly;
		yellow - the system may be functioning suboptimally;
		red - the system requires attention to function correctly;
		blue - the system's status is unknown or incomplete;
		gray - the system is intentionally not functioning (offline);
		black - the system is not connected to any peers."
	::= { sysCmFailoverStatus 3 } 

sysCmFailoverStatusSummary OBJECT-TYPE 
	SYNTAX LongDisplayString
	MAX-ACCESS read-only
	STATUS current
	DESCRIPTION
		"The summary of the failover status on the system."
	::= { sysCmFailoverStatus 4 } 

--==================================================================
-- Cmi_failover_status_details
--==================================================================
sysCmFailoverStatusDetailsNumber OBJECT-TYPE 
	SYNTAX INTEGER
	MAX-ACCESS read-only
	STATUS current
	DESCRIPTION
		"The number of sysCmFailoverStatusDetails entries in the table."
	::= { sysCmFailoverStatusDetails 1 } 

sysCmFailoverStatusDetailsTable OBJECT-TYPE
	SYNTAX SEQUENCE OF SysCmFailoverStatusDetailsEntry
	MAX-ACCESS not-accessible
	STATUS current
	DESCRIPTION
		"A table containing details of failover status on the system."
	::= { sysCmFailoverStatusDetails 2 } 

sysCmFailoverStatusDetailsEntry OBJECT-TYPE
	SYNTAX  SysCmFailoverStatusDetailsEntry
	MAX-ACCESS not-accessible
	STATUS current
	DESCRIPTION
		"Columns in the sysCmFailoverStatusDetails Table"
	INDEX {
		sysCmFailoverStatusDetailsIndex
	}
	::= { sysCmFailoverStatusDetailsTable 1 } 

SysCmFailoverStatusDetailsEntry ::= 
	SEQUENCE {
        	sysCmFailoverStatusDetailsIndex                        INTEGER,
        	sysCmFailoverStatusDetailsDetails                      LongDisplayString
	}

sysCmFailoverStatusDetailsIndex OBJECT-TYPE 
	SYNTAX INTEGER(1..2147483647)
	MAX-ACCESS read-only
	STATUS current
	DESCRIPTION
		"The index of the table that contains the details of the failover status
		on the system."
	::= { sysCmFailoverStatusDetailsEntry 1 } 

sysCmFailoverStatusDetailsDetails OBJECT-TYPE 
	SYNTAX LongDisplayString
	MAX-ACCESS read-only
	STATUS current
	DESCRIPTION
		"The details of the failover status on the system."
	::= { sysCmFailoverStatusDetailsEntry 2 } 

--==================================================================
-- Traffic_group_device
--==================================================================
sysCmTrafficGroupStatusNumber OBJECT-TYPE 
	SYNTAX INTEGER
	MAX-ACCESS read-only
	STATUS current
	DESCRIPTION
		"The number of sysCmTrafficGroupStatus entries in the table."
	::= { sysCmTrafficGroupStatus 1 } 

sysCmTrafficGroupStatusTable OBJECT-TYPE
	SYNTAX SEQUENCE OF SysCmTrafficGroupStatusEntry
	MAX-ACCESS not-accessible
	STATUS current
	DESCRIPTION
		"A table containing information of traffic group(s) status on the system."
	::= { sysCmTrafficGroupStatus 2 } 

sysCmTrafficGroupStatusEntry OBJECT-TYPE
	SYNTAX  SysCmTrafficGroupStatusEntry
	MAX-ACCESS not-accessible
	STATUS current
	DESCRIPTION
		"Columns in the sysCmTrafficGroupStatus Table"
	INDEX {
		sysCmTrafficGroupStatusTrafficGroup,
		sysCmTrafficGroupStatusDeviceName
	}
	::= { sysCmTrafficGroupStatusTable 1 } 

SysCmTrafficGroupStatusEntry ::= 
	SEQUENCE {
        	sysCmTrafficGroupStatusTrafficGroup                    LongDisplayString,
        	sysCmTrafficGroupStatusDeviceName                      LongDisplayString,
        	sysCmTrafficGroupStatusFailoverStatus                  INTEGER
	}

sysCmTrafficGroupStatusTrafficGroup OBJECT-TYPE 
	SYNTAX LongDisplayString
	MAX-ACCESS read-only
	STATUS current
	DESCRIPTION
		"The name of the traffic group."
	::= { sysCmTrafficGroupStatusEntry 1 } 

sysCmTrafficGroupStatusDeviceName OBJECT-TYPE 
	SYNTAX LongDisplayString
	MAX-ACCESS read-only
	STATUS current
	DESCRIPTION
		"The name of the device."
	::= { sysCmTrafficGroupStatusEntry 2 } 

sysCmTrafficGroupStatusFailoverStatus OBJECT-TYPE 
	SYNTAX INTEGER {
		unknown(0),
		offline(1),
		forcedOffline(2),
		standby(3),
		active(4)
	}
	MAX-ACCESS read-only
	STATUS current
	DESCRIPTION
		"The failover status of the device within the traffic group.
		unknown - the failover status of the device is unknown;
		offline - the device is offline;
		forcedOffline - the device is forced offline;
		standby - the device is standby;
		active - the device  is active."
	::= { sysCmTrafficGroupStatusEntry 3 } 

--==================================================================
-- Global_dns_stat
--==================================================================
sysDnsStatResetStats OBJECT-TYPE 
	SYNTAX INTEGER
	MAX-ACCESS read-write
	STATUS current
	DESCRIPTION
		"The action to reset resetable statistics data in  sysGlobalDnsStat. 
		 Setting this value to 1 will reset statistics data. 
		 Note, some statistics data may not be reset including data that are incremental counters."
	::= { sysGlobalDnsStat 1 } 

sysDnsStatQueries OBJECT-TYPE 
	SYNTAX Counter64
	MAX-ACCESS read-only
	STATUS current
	DESCRIPTION
		"The total number of DNS queries."
	::= { sysGlobalDnsStat 2 } 

sysDnsStatResponses OBJECT-TYPE 
	SYNTAX Counter64
	MAX-ACCESS read-only
	STATUS current
	DESCRIPTION
		"The total number of DNS responses."
	::= { sysGlobalDnsStat 3 } 

sysDnsStatResponsesPerSec OBJECT-TYPE 
	SYNTAX Counter64
	MAX-ACCESS read-only
	STATUS current
	DESCRIPTION
		"The average number of DNS responses per second."
	::= { sysGlobalDnsStat 4 } 

sysDnsStatToGtm OBJECT-TYPE 
	SYNTAX Counter64
	MAX-ACCESS read-only
	STATUS current
	DESCRIPTION
		"The number of requests sent to GTM."
	::= { sysGlobalDnsStat 5 } 

sysDnsStatDnsExpressReqs OBJECT-TYPE 
	SYNTAX Counter64
	MAX-ACCESS read-only
	STATUS current
	DESCRIPTION
		"The number of DNS Express requests."
	::= { sysGlobalDnsStat 6 } 

sysDnsStatDnsExpressNotifies OBJECT-TYPE 
	SYNTAX Counter64
	MAX-ACCESS read-only
	STATUS current
	DESCRIPTION
		"The number of DNS Express notifies."
	::= { sysGlobalDnsStat 7 } 

sysDnsStatToCache OBJECT-TYPE 
	SYNTAX Counter64
	MAX-ACCESS read-only
	STATUS current
	DESCRIPTION
		"The number of requests sent to the DNS cache."
	::= { sysGlobalDnsStat 8 } 

sysDnsStatToDns OBJECT-TYPE 
	SYNTAX Counter64
	MAX-ACCESS read-only
	STATUS current
	DESCRIPTION
		"The number of requests sent to backend DNS."
	::= { sysGlobalDnsStat 9 } 

sysDnsStatDns64Reqs OBJECT-TYPE 
	SYNTAX Counter64
	MAX-ACCESS read-only
	STATUS current
	DESCRIPTION
		"The number of A requests the system generated and sent."
	::= { sysGlobalDnsStat 10 } 

sysDnsStatDns64Rewrites OBJECT-TYPE 
	SYNTAX Counter64
	MAX-ACCESS read-only
	STATUS current
	DESCRIPTION
		"The number of A responses translated to AAAA."
	::= { sysGlobalDnsStat 11 } 

sysDnsStatDns64Failures OBJECT-TYPE 
	SYNTAX Counter64
	MAX-ACCESS read-only
	STATUS current
	DESCRIPTION
		"The number of unsuccessful AAAA requests."
	::= { sysGlobalDnsStat 12 } 

sysDnsStatHints OBJECT-TYPE 
	SYNTAX Counter64
	MAX-ACCESS read-only
	STATUS current
	DESCRIPTION
		"The number of hint (Root Nameservers) responses sent."
	::= { sysGlobalDnsStat 13 } 

sysDnsStatRejects OBJECT-TYPE 
	SYNTAX Counter64
	MAX-ACCESS read-only
	STATUS current
	DESCRIPTION
		"The number of reject (REFUSED) responses sent."
	::= { sysGlobalDnsStat 14 } 

sysDnsStatNoErrors OBJECT-TYPE 
	SYNTAX Counter64
	MAX-ACCESS read-only
	STATUS current
	DESCRIPTION
		"The number of NOERROR responses sent."
	::= { sysGlobalDnsStat 15 } 

sysDnsStatDrops OBJECT-TYPE 
	SYNTAX Counter64
	MAX-ACCESS read-only
	STATUS current
	DESCRIPTION
		"The number of packets dropped (not sent to GTM, DNS-Express, DNSSEC,
		DNS64, or Backend DNS (e.g. BIND))."
	::= { sysGlobalDnsStat 16 } 

sysDnsStatMalformed OBJECT-TYPE 
	SYNTAX Counter64
	MAX-ACCESS read-only
	STATUS current
	DESCRIPTION
		"The number of malformed packets received."
	::= { sysGlobalDnsStat 17 } 

sysDnsStatTclSuspends OBJECT-TYPE 
	SYNTAX Counter64
	MAX-ACCESS read-only
	STATUS current
	DESCRIPTION
		"The number of TCL suspends."
	::= { sysGlobalDnsStat 18 } 

sysDnsStatRecursionDesired OBJECT-TYPE 
	SYNTAX Counter64
	MAX-ACCESS read-only
	STATUS current
	DESCRIPTION
		"The number of queries with RD bit set."
	::= { sysGlobalDnsStat 19 } 

sysDnsStatCheckingDisabled OBJECT-TYPE 
	SYNTAX Counter64
	MAX-ACCESS read-only
	STATUS current
	DESCRIPTION
		"The number of queries with CD bit set."
	::= { sysGlobalDnsStat 20 } 

sysDnsStatEdns0 OBJECT-TYPE 
	SYNTAX Counter64
	MAX-ACCESS read-only
	STATUS current
	DESCRIPTION
		"The number of queries with EDNS0 bit set."
	::= { sysGlobalDnsStat 21 } 

sysDnsStatOpcodeQuery OBJECT-TYPE 
	SYNTAX Counter64
	MAX-ACCESS read-only
	STATUS current
	DESCRIPTION
		"The number of queries whose operation code is QUERY."
	::= { sysGlobalDnsStat 22 } 

sysDnsStatOpcodeNotify OBJECT-TYPE 
	SYNTAX Counter64
	MAX-ACCESS read-only
	STATUS current
	DESCRIPTION
		"The number of queries whose operation code is NOTIFY."
	::= { sysGlobalDnsStat 23 } 

sysDnsStatOpcodeUpdate OBJECT-TYPE 
	SYNTAX Counter64
	MAX-ACCESS read-only
	STATUS current
	DESCRIPTION
		"The number of queries whose operation code is UPDATE."
	::= { sysGlobalDnsStat 24 } 

sysDnsStatZoneIxfr OBJECT-TYPE 
	SYNTAX Counter64
	MAX-ACCESS read-only
	STATUS current
	DESCRIPTION
		"The number of queries whose question type is IXFR."
	::= { sysGlobalDnsStat 25 } 

sysDnsStatZoneAxfr OBJECT-TYPE 
	SYNTAX Counter64
	MAX-ACCESS read-only
	STATUS current
	DESCRIPTION
		"The number of queries whose question type is AXFR."
	::= { sysGlobalDnsStat 26 } 

sysDnsStatAuthoritativeAnswer OBJECT-TYPE 
	SYNTAX Counter64
	MAX-ACCESS read-only
	STATUS current
	DESCRIPTION
		"The number of responses with AA bit set."
	::= { sysGlobalDnsStat 27 } 

sysDnsStatRecursionAvailable OBJECT-TYPE 
	SYNTAX Counter64
	MAX-ACCESS read-only
	STATUS current
	DESCRIPTION
		"The number of responses with RA bit set."
	::= { sysGlobalDnsStat 28 } 

sysDnsStatAuthenticatedData OBJECT-TYPE 
	SYNTAX Counter64
	MAX-ACCESS read-only
	STATUS current
	DESCRIPTION
		"The number of responses with AD bit set."
	::= { sysGlobalDnsStat 29 } 

sysDnsStatTruncated OBJECT-TYPE 
	SYNTAX Counter64
	MAX-ACCESS read-only
	STATUS current
	DESCRIPTION
		"The number of responses with TC bit set."
	::= { sysGlobalDnsStat 30 } 

sysDnsStatRcodeNoerror OBJECT-TYPE 
	SYNTAX Counter64
	MAX-ACCESS read-only
	STATUS current
	DESCRIPTION
		"The number of responses whose return code is NOERROR."
	::= { sysGlobalDnsStat 31 } 

sysDnsStatRcodeNxdomain OBJECT-TYPE 
	SYNTAX Counter64
	MAX-ACCESS read-only
	STATUS current
	DESCRIPTION
		"The number of responses whose return code is NXDOMAIN."
	::= { sysGlobalDnsStat 32 } 

sysDnsStatRcodeServfail OBJECT-TYPE 
	SYNTAX Counter64
	MAX-ACCESS read-only
	STATUS current
	DESCRIPTION
		"The number of responses whose return code is SERVFAIL."
	::= { sysGlobalDnsStat 33 } 

sysDnsStatRcodeRefused OBJECT-TYPE 
	SYNTAX Counter64
	MAX-ACCESS read-only
	STATUS current
	DESCRIPTION
		"The number of responses whose return code is REFUSED."
	::= { sysGlobalDnsStat 34 } 

sysDnsStatMalicious OBJECT-TYPE 
	SYNTAX Counter64
	MAX-ACCESS read-only
	STATUS current
	DESCRIPTION
		"The number of malicious packets received."
	::= { sysGlobalDnsStat 35 } 

sysDnsStatAReqs OBJECT-TYPE 
	SYNTAX Counter64
	MAX-ACCESS read-only
	STATUS current
	DESCRIPTION
		"The number of A query packets received."
	::= { sysGlobalDnsStat 36 } 

sysDnsStatAaaaReqs OBJECT-TYPE 
	SYNTAX Counter64
	MAX-ACCESS read-only
	STATUS current
	DESCRIPTION
		"The number of AAAA query packets received."
	::= { sysGlobalDnsStat 37 } 

sysDnsStatAnyReqs OBJECT-TYPE 
	SYNTAX Counter64
	MAX-ACCESS read-only
	STATUS current
	DESCRIPTION
		"The number of ANY type query packets received."
	::= { sysGlobalDnsStat 38 } 

sysDnsStatCnameReqs OBJECT-TYPE 
	SYNTAX Counter64
	MAX-ACCESS read-only
	STATUS current
	DESCRIPTION
		"The number of CNAME query packets received."
	::= { sysGlobalDnsStat 39 } 

sysDnsStatMxReqs OBJECT-TYPE 
	SYNTAX Counter64
	MAX-ACCESS read-only
	STATUS current
	DESCRIPTION
		"The number of MX query packets received."
	::= { sysGlobalDnsStat 40 } 

sysDnsStatNsReqs OBJECT-TYPE 
	SYNTAX Counter64
	MAX-ACCESS read-only
	STATUS current
	DESCRIPTION
		"The number of NS query packets received."
	::= { sysGlobalDnsStat 41 } 

sysDnsStatPtrReqs OBJECT-TYPE 
	SYNTAX Counter64
	MAX-ACCESS read-only
	STATUS current
	DESCRIPTION
		"The number of PTR query packets received."
	::= { sysGlobalDnsStat 42 } 

sysDnsStatSoaReqs OBJECT-TYPE 
	SYNTAX Counter64
	MAX-ACCESS read-only
	STATUS current
	DESCRIPTION
		"The number of SOA query packets received."
	::= { sysGlobalDnsStat 43 } 

sysDnsStatSrvReqs OBJECT-TYPE 
	SYNTAX Counter64
	MAX-ACCESS read-only
	STATUS current
	DESCRIPTION
		"The number of SRV query packets received."
	::= { sysGlobalDnsStat 44 } 

sysDnsStatTxtReqs OBJECT-TYPE 
	SYNTAX Counter64
	MAX-ACCESS read-only
	STATUS current
	DESCRIPTION
		"The number of TXT query packets received."
	::= { sysGlobalDnsStat 45 } 

sysDnsStatOtherReqs OBJECT-TYPE 
	SYNTAX Counter64
	MAX-ACCESS read-only
	STATUS current
	DESCRIPTION
		"The number of uncategorized DNS packets received."
	::= { sysGlobalDnsStat 46 } 

--==================================================================
-- Global_lsn_pool_stat
--==================================================================
sysLsnPoolStatResetStats OBJECT-TYPE 
	SYNTAX INTEGER
	MAX-ACCESS read-write
	STATUS current
	DESCRIPTION
		"The action to reset resetable statistics data in  sysGlobalLsnPoolStat. 
		 Setting this value to 1 will reset statistics data. 
		 Note, some statistics data may not be reset including data that are incremental counters."
	::= { sysGlobalLsnPoolStat 1 } 

sysLsnPoolStatActivePersistenceMappings OBJECT-TYPE 
	SYNTAX Counter64
	MAX-ACCESS read-only
	STATUS current
	DESCRIPTION
		"The number of active persistence mappings."
	::= { sysGlobalLsnPoolStat 2 } 

sysLsnPoolStatActiveInboundReservations OBJECT-TYPE 
	SYNTAX Counter64
	MAX-ACCESS read-only
	STATUS current
	DESCRIPTION
		"The number of active inbound reservations."
	::= { sysGlobalLsnPoolStat 3 } 

sysLsnPoolStatTranslationRequests OBJECT-TYPE 
	SYNTAX Counter64
	MAX-ACCESS read-only
	STATUS current
	DESCRIPTION
		"The number of translation requests."
	::= { sysGlobalLsnPoolStat 4 } 

sysLsnPoolStatHairpinConnectionRequests OBJECT-TYPE 
	SYNTAX Counter64
	MAX-ACCESS read-only
	STATUS current
	DESCRIPTION
		"The number of hairpin connection requests."
	::= { sysGlobalLsnPoolStat 5 } 

sysLsnPoolStatActiveTranslations OBJECT-TYPE 
	SYNTAX Counter64
	MAX-ACCESS read-only
	STATUS current
	DESCRIPTION
		"The number of active translations."
	::= { sysGlobalLsnPoolStat 6 } 

sysLsnPoolStatActiveHairpinConnections OBJECT-TYPE 
	SYNTAX Counter64
	MAX-ACCESS read-only
	STATUS current
	DESCRIPTION
		"The number of active hairpin connections."
	::= { sysGlobalLsnPoolStat 7 } 

sysLsnPoolStatTranslationRequestFailures OBJECT-TYPE 
	SYNTAX Counter64
	MAX-ACCESS read-only
	STATUS current
	DESCRIPTION
		"The number of translation request failures."
	::= { sysGlobalLsnPoolStat 8 } 

sysLsnPoolStatPersistenceMappingFailures OBJECT-TYPE 
	SYNTAX Counter64
	MAX-ACCESS read-only
	STATUS current
	DESCRIPTION
		"The number of persistence mapping translation failures."
	::= { sysGlobalLsnPoolStat 9 } 

sysLsnPoolStatHairpinConnectionFailures OBJECT-TYPE 
	SYNTAX Counter64
	MAX-ACCESS read-only
	STATUS current
	DESCRIPTION
		"The number of failed hairpin connection attempts.  A hairpin connection failure occurs when 
	        a subscriber connects to an inbound reservation but a connection could not be created."
	::= { sysGlobalLsnPoolStat 10 } 

sysLsnPoolStatBackupPoolTranslations OBJECT-TYPE 
	SYNTAX Counter64
	MAX-ACCESS read-only
	STATUS current
	DESCRIPTION
		"The number of translation requests that were served using the backup pool."
	::= { sysGlobalLsnPoolStat 11 } 

sysLsnPoolStatLogAttempts OBJECT-TYPE 
	SYNTAX Counter64
	MAX-ACCESS read-only
	STATUS current
	DESCRIPTION
		"The number of logging attempts."
	::= { sysGlobalLsnPoolStat 12 } 

sysLsnPoolStatLogFailures OBJECT-TYPE 
	SYNTAX Counter64
	MAX-ACCESS read-only
	STATUS current
	DESCRIPTION
		"The number of logging attempts that resulted in failures."
	::= { sysGlobalLsnPoolStat 13 } 

--==================================================================
-- Fec_stat
--==================================================================
sysFecStatResetStats OBJECT-TYPE 
	SYNTAX INTEGER
	MAX-ACCESS read-write
	STATUS current
	DESCRIPTION
		"The action to reset resetable statistics data in  sysFecStat. 
		 Setting this value to 1 will reset statistics data. 
		 Note, some statistics data may not be reset including data that are incremental counters."
	::= { sysFecStat 1 } 

sysFecStatNumber OBJECT-TYPE 
	SYNTAX INTEGER
	MAX-ACCESS read-only
	STATUS current
	DESCRIPTION
		"The number of sysFecStat entries in the table."
	::= { sysFecStat 2 } 

sysFecStatTable OBJECT-TYPE
	SYNTAX SEQUENCE OF SysFecStatEntry
	MAX-ACCESS not-accessible
	STATUS current
	DESCRIPTION
		"A table containing statistics information about FEC tunnels."
	::= { sysFecStat 3 } 

sysFecStatEntry OBJECT-TYPE
	SYNTAX  SysFecStatEntry
	MAX-ACCESS not-accessible
	STATUS current
	DESCRIPTION
		"Columns in the sysFecStat Table"
	INDEX {
		sysFecStatName,
		sysFecStatProfile
	}
	::= { sysFecStatTable 1 } 

SysFecStatEntry ::= 
	SEQUENCE {
        	sysFecStatName                                         LongDisplayString,
        	sysFecStatProfile                                      LongDisplayString,
        	sysFecStatOutRawPackets                                Counter64,
        	sysFecStatOutRawBytes                                  Counter64,
        	sysFecStatOutRdndPackets                               Counter64,
        	sysFecStatOutRdndBytes                                 Counter64,
        	sysFecStatInRawPackets                                 Counter64,
        	sysFecStatInRawBytes                                   Counter64,
        	sysFecStatInRdndPackets                                Counter64,
        	sysFecStatInRdndBytes                                  Counter64,
        	sysFecStatInRdndLost                                   Counter64,
        	sysFecStatInRawLost                                    Counter64,
        	sysFecStatRmtInRdndPackets                             Counter64,
        	sysFecStatRmtInRdndLost                                Counter64,
        	sysFecStatRmtInRawPackets                              Counter64,
        	sysFecStatRmtInRawLost                                 Counter64
	}

sysFecStatName OBJECT-TYPE 
	SYNTAX LongDisplayString
	MAX-ACCESS read-only
	STATUS current
	DESCRIPTION
		"The name of a FEC tunnel."
	::= { sysFecStatEntry 1 } 

sysFecStatProfile OBJECT-TYPE 
	SYNTAX LongDisplayString
	MAX-ACCESS read-only
	STATUS current
	DESCRIPTION
		"The name of a FEC profile."
	::= { sysFecStatEntry 2 } 

sysFecStatOutRawPackets OBJECT-TYPE 
	SYNTAX Counter64
	MAX-ACCESS read-only
	STATUS current
	DESCRIPTION
		"The number of output raw packets."
	::= { sysFecStatEntry 3 } 

sysFecStatOutRawBytes OBJECT-TYPE 
	SYNTAX Counter64
	MAX-ACCESS read-only
	STATUS current
	DESCRIPTION
		"The number of output raw bytes."
	::= { sysFecStatEntry 4 } 

sysFecStatOutRdndPackets OBJECT-TYPE 
	SYNTAX Counter64
	MAX-ACCESS read-only
	STATUS current
	DESCRIPTION
		"The number of output redundant packets."
	::= { sysFecStatEntry 5 } 

sysFecStatOutRdndBytes OBJECT-TYPE 
	SYNTAX Counter64
	MAX-ACCESS read-only
	STATUS current
	DESCRIPTION
		"The number of output redundant bytes."
	::= { sysFecStatEntry 6 } 

sysFecStatInRawPackets OBJECT-TYPE 
	SYNTAX Counter64
	MAX-ACCESS read-only
	STATUS current
	DESCRIPTION
		"The number of input raw packets."
	::= { sysFecStatEntry 7 } 

sysFecStatInRawBytes OBJECT-TYPE 
	SYNTAX Counter64
	MAX-ACCESS read-only
	STATUS current
	DESCRIPTION
		"The number of input raw bytes."
	::= { sysFecStatEntry 8 } 

sysFecStatInRdndPackets OBJECT-TYPE 
	SYNTAX Counter64
	MAX-ACCESS read-only
	STATUS current
	DESCRIPTION
		"The number of input redundant packets."
	::= { sysFecStatEntry 9 } 

sysFecStatInRdndBytes OBJECT-TYPE 
	SYNTAX Counter64
	MAX-ACCESS read-only
	STATUS current
	DESCRIPTION
		"The number of input redundant bytes."
	::= { sysFecStatEntry 10 } 

sysFecStatInRdndLost OBJECT-TYPE 
	SYNTAX Counter64
	MAX-ACCESS read-only
	STATUS current
	DESCRIPTION
		"The number of input redundant packets lost."
	::= { sysFecStatEntry 11 } 

sysFecStatInRawLost OBJECT-TYPE 
	SYNTAX Counter64
	MAX-ACCESS read-only
	STATUS current
	DESCRIPTION
		"The number of input raw packets lost."
	::= { sysFecStatEntry 12 } 

sysFecStatRmtInRdndPackets OBJECT-TYPE 
	SYNTAX Counter64
	MAX-ACCESS read-only
	STATUS current
	DESCRIPTION
		"The number of remote side input redundant packets."
	::= { sysFecStatEntry 13 } 

sysFecStatRmtInRdndLost OBJECT-TYPE 
	SYNTAX Counter64
	MAX-ACCESS read-only
	STATUS current
	DESCRIPTION
		"The number of remote side input redundant packets lost."
	::= { sysFecStatEntry 14 } 

sysFecStatRmtInRawPackets OBJECT-TYPE 
	SYNTAX Counter64
	MAX-ACCESS read-only
	STATUS current
	DESCRIPTION
		"The number of remote side input raw packets."
	::= { sysFecStatEntry 15 } 

sysFecStatRmtInRawLost OBJECT-TYPE 
	SYNTAX Counter64
	MAX-ACCESS read-only
	STATUS current
	DESCRIPTION
		"The number of remote side input raw packets lost."
	::= { sysFecStatEntry 16 } 

--==================================================================
-- Vcmp_assigned_slots
--==================================================================
sysVcmpAssignedSlotsNumber OBJECT-TYPE 
	SYNTAX INTEGER
	MAX-ACCESS read-only
	STATUS current
	DESCRIPTION
		"The number of sysVcmpAssignedSlots entries in the table."
	::= { sysVcmpAssignedSlots 1 } 

sysVcmpAssignedSlotsTable OBJECT-TYPE
	SYNTAX SEQUENCE OF SysVcmpAssignedSlotsEntry
	MAX-ACCESS not-accessible
	STATUS current
	DESCRIPTION
		"A list of the slots assigned to a VCMP guest."
	::= { sysVcmpAssignedSlots 2 } 

sysVcmpAssignedSlotsEntry OBJECT-TYPE
	SYNTAX  SysVcmpAssignedSlotsEntry
	MAX-ACCESS not-accessible
	STATUS current
	DESCRIPTION
		"Columns in the sysVcmpAssignedSlots Table"
	INDEX {
		sysVcmpAssignedSlotsName,
		sysVcmpAssignedSlotsIndex
	}
	::= { sysVcmpAssignedSlotsTable 1 } 

SysVcmpAssignedSlotsEntry ::= 
	SEQUENCE {
        	sysVcmpAssignedSlotsName                               LongDisplayString,
        	sysVcmpAssignedSlotsIndex                              INTEGER,
        	sysVcmpAssignedSlotsSlotId                             INTEGER
	}

sysVcmpAssignedSlotsName OBJECT-TYPE 
	SYNTAX LongDisplayString
	MAX-ACCESS read-only
	STATUS current
	DESCRIPTION
		"The name of a VCMP guest."
	::= { sysVcmpAssignedSlotsEntry 1 } 

sysVcmpAssignedSlotsIndex OBJECT-TYPE 
	SYNTAX INTEGER(1..2147483647)
	MAX-ACCESS read-only
	STATUS current
	DESCRIPTION
		"The index of the slot number assigned to the specified VCMP guest."
	::= { sysVcmpAssignedSlotsEntry 2 } 

sysVcmpAssignedSlotsSlotId OBJECT-TYPE 
	SYNTAX INTEGER
	MAX-ACCESS read-only
	STATUS current
	DESCRIPTION
		"The slot number assigned to the specified VCMP guest."
	::= { sysVcmpAssignedSlotsEntry 3 } 

--==================================================================
-- Vcmp_allowed_slots
--==================================================================
sysVcmpAllowedSlotsNumber OBJECT-TYPE 
	SYNTAX INTEGER
	MAX-ACCESS read-only
	STATUS current
	DESCRIPTION
		"The number of sysVcmpAllowedSlots entries in the table."
	::= { sysVcmpAllowedSlots 1 } 

sysVcmpAllowedSlotsTable OBJECT-TYPE
	SYNTAX SEQUENCE OF SysVcmpAllowedSlotsEntry
	MAX-ACCESS not-accessible
	STATUS current
	DESCRIPTION
		"A list of the slots that are allowed to be assigned to a VCMP guest."
	::= { sysVcmpAllowedSlots 2 } 

sysVcmpAllowedSlotsEntry OBJECT-TYPE
	SYNTAX  SysVcmpAllowedSlotsEntry
	MAX-ACCESS not-accessible
	STATUS current
	DESCRIPTION
		"Columns in the sysVcmpAllowedSlots Table"
	INDEX {
		sysVcmpAllowedSlotsName,
		sysVcmpAllowedSlotsIndex
	}
	::= { sysVcmpAllowedSlotsTable 1 } 

SysVcmpAllowedSlotsEntry ::= 
	SEQUENCE {
        	sysVcmpAllowedSlotsName                                LongDisplayString,
        	sysVcmpAllowedSlotsIndex                               INTEGER,
        	sysVcmpAllowedSlotsSlotId                              INTEGER
	}

sysVcmpAllowedSlotsName OBJECT-TYPE 
	SYNTAX LongDisplayString
	MAX-ACCESS read-only
	STATUS current
	DESCRIPTION
		"The name of a VCMP guest."
	::= { sysVcmpAllowedSlotsEntry 1 } 

sysVcmpAllowedSlotsIndex OBJECT-TYPE 
	SYNTAX INTEGER(1..2147483647)
	MAX-ACCESS read-only
	STATUS current
	DESCRIPTION
		"The index of a slot number allowed for the specified VCMP guest."
	::= { sysVcmpAllowedSlotsEntry 2 } 

sysVcmpAllowedSlotsSlotId OBJECT-TYPE 
	SYNTAX INTEGER
	MAX-ACCESS read-only
	STATUS current
	DESCRIPTION
		"A slot number allowed for the specified VCMP guest."
	::= { sysVcmpAllowedSlotsEntry 3 } 

--==================================================================
-- Virtual_disk
--==================================================================
sysVirtualDiskNumber OBJECT-TYPE 
	SYNTAX INTEGER
	MAX-ACCESS read-only
	STATUS current
	DESCRIPTION
		"The number of sysVirtualDisk entries in the table."
	::= { sysVirtualDisk 1 } 

sysVirtualDiskTable OBJECT-TYPE
	SYNTAX SEQUENCE OF SysVirtualDiskEntry
	MAX-ACCESS not-accessible
	STATUS current
	DESCRIPTION
		"A list of virtual disks for the VCMP guest VMs on the appliance or on each slot."
	::= { sysVirtualDisk 2 } 

sysVirtualDiskEntry OBJECT-TYPE
	SYNTAX  SysVirtualDiskEntry
	MAX-ACCESS not-accessible
	STATUS current
	DESCRIPTION
		"Columns in the sysVirtualDisk Table"
	INDEX {
		sysVirtualDiskSlotId,
		sysVirtualDiskFilename
	}
	::= { sysVirtualDiskTable 1 } 

SysVirtualDiskEntry ::= 
	SEQUENCE {
        	sysVirtualDiskFilename                                 LongDisplayString,
        	sysVirtualDiskOperatingSystem                          INTEGER,
        	sysVirtualDiskSlotId                                   INTEGER,
        	sysVirtualDiskState                                    INTEGER
	}

sysVirtualDiskFilename OBJECT-TYPE 
	SYNTAX LongDisplayString
	MAX-ACCESS read-only
	STATUS current
	DESCRIPTION
		"Virtual disk image filename on the host."
	::= { sysVirtualDiskEntry 1 } 

sysVirtualDiskOperatingSystem OBJECT-TYPE 
	SYNTAX INTEGER {
		unknown(0),
		tmos(1),
		linux(2)
	}
	MAX-ACCESS read-only
	STATUS current
	DESCRIPTION
		"The guest operating system installed on the virtual disk."
	::= { sysVirtualDiskEntry 2 } 

sysVirtualDiskSlotId OBJECT-TYPE 
	SYNTAX INTEGER(1..2147483647)
	MAX-ACCESS read-only
	STATUS current
	DESCRIPTION
		"The chassis slot number of this virtual disk."
	::= { sysVirtualDiskEntry 3 } 

sysVirtualDiskState OBJECT-TYPE 
	SYNTAX INTEGER {
		unknown(0),
		created(1),
		installing(2),
		migrating(3),
		ready(4),
		in-use(5)
	}
	MAX-ACCESS read-only
	STATUS current
	DESCRIPTION
		"The status of this virtual disk."
	::= { sysVirtualDiskEntry 4 } 

--================================================================
 -- Compliance and Group
--================================================================

bigipSystemCompliance	MODULE-COMPLIANCE 
	STATUS current
	DESCRIPTION
		"This specifies the objects that are required to claim 
                 compliance to F5 Traffic Management System."
	MODULE
	  MANDATORY-GROUPS { bigipSystemGroups } 
	::= { bigipCompliances 1 } 

bigipSystemGroups  OBJECT IDENTIFIER ::= {  bigipGroups 1 }

sysAttrGroup OBJECT-GROUP
	 OBJECTS {
		sysAttrArpMaxEntries,
		sysAttrArpAddReciprocal,
		sysAttrArpTimeout,
		sysAttrArpRetries,
		sysAttrBootQuiet,
		sysAttrConfigsyncState,
		sysAttrConnAdaptiveReaperHiwat,
		sysAttrConnAdaptiveReaperLowat,
		sysAttrConnAutoLasthop,
		sysAttrFailoverActiveMode,
		sysAttrFailoverForceActive,
		sysAttrFailoverForceStandby,
		sysAttrFailoverIsRedundant,
		sysAttrFailoverMemoryRestartPercent,
		sysAttrFailoverNetwork,
		sysAttrFailoverStandbyLinkDownTime,
		sysAttrFailoverSslhardware,
		sysAttrFailoverSslhardwareAction,
		sysAttrFailoverUnitMask,
		sysAttrFailoverUnitId,
		sysAttrModeMaint,
		sysAttrPacketFilter,
		sysAttrPacketFilterAllowImportantIcmp,
		sysAttrPacketFilterEstablished,
		sysAttrPacketFilterDefaultAction,
		sysAttrPacketFilterSendIcmpErrors,
		sysAttrPvaAcceleration,
		sysAttrVlanFDBTimeout,
		sysAttrWatchdogState
	}
	STATUS	 current
	DESCRIPTION
		"A collection of objects of sysGlobalAttr MIB."
	::= { bigipSystemGroups 1 }

sysStatGroup OBJECT-GROUP
	 OBJECTS {
		sysStatResetStats,
		sysStatClientPktsIn,
		sysStatClientBytesIn,
		sysStatClientPktsOut,
		sysStatClientBytesOut,
		sysStatClientMaxConns,
		sysStatClientTotConns,
		sysStatClientCurConns,
		sysStatServerPktsIn,
		sysStatServerBytesIn,
		sysStatServerPktsOut,
		sysStatServerBytesOut,
		sysStatServerMaxConns,
		sysStatServerTotConns,
		sysStatServerCurConns,
		sysStatPvaClientPktsIn,
		sysStatPvaClientBytesIn,
		sysStatPvaClientPktsOut,
		sysStatPvaClientBytesOut,
		sysStatPvaClientMaxConns,
		sysStatPvaClientTotConns,
		sysStatPvaClientCurConns,
		sysStatPvaServerPktsIn,
		sysStatPvaServerBytesIn,
		sysStatPvaServerPktsOut,
		sysStatPvaServerBytesOut,
		sysStatPvaServerMaxConns,
		sysStatPvaServerTotConns,
		sysStatPvaServerCurConns,
		sysStatTotPvaAssistConn,
		sysStatCurrPvaAssistConn,
		sysStatMaintenanceModeDeny,
		sysStatMaxConnVirtualPathDeny,
		sysStatVirtualServerNonSynDeny,
		sysStatNoHandlerDeny,
		sysStatLicenseDeny,
		sysStatConnectionMemoryErrors,
		sysStatCpuCount,
		sysStatActiveCpuCount,
		sysStatMultiProcessorMode,
		sysStatTmTotalCycles,
		sysStatTmIdleCycles,
		sysStatTmSleepCycles,
		sysStatMemoryTotal,
		sysStatMemoryUsed,
		sysStatDroppedPackets,
		sysStatIncomingPacketErrors,
		sysStatOutgoingPacketErrors,
		sysStatAuthTotSessions,
		sysStatAuthCurSessions,
		sysStatAuthMaxSessions,
		sysStatAuthSuccessResults,
		sysStatAuthFailureResults,
		sysStatAuthWantcredentialResults,
		sysStatAuthErrorResults,
		sysStatHttpRequests,
		sysStatHardSyncookieGen,
		sysStatHardSyncookieDet,
		sysStatClientPktsIn5s,
		sysStatClientBytesIn5s,
		sysStatClientPktsOut5s,
		sysStatClientBytesOut5s,
		sysStatClientMaxConns5s,
		sysStatClientTotConns5s,
		sysStatClientCurConns5s,
		sysStatServerPktsIn5s,
		sysStatServerBytesIn5s,
		sysStatServerPktsOut5s,
		sysStatServerBytesOut5s,
		sysStatServerMaxConns5s,
		sysStatServerTotConns5s,
		sysStatServerCurConns5s,
		sysStatClientPktsIn1m,
		sysStatClientBytesIn1m,
		sysStatClientPktsOut1m,
		sysStatClientBytesOut1m,
		sysStatClientMaxConns1m,
		sysStatClientTotConns1m,
		sysStatClientCurConns1m,
		sysStatServerPktsIn1m,
		sysStatServerBytesIn1m,
		sysStatServerPktsOut1m,
		sysStatServerBytesOut1m,
		sysStatServerMaxConns1m,
		sysStatServerTotConns1m,
		sysStatServerCurConns1m,
		sysStatClientPktsIn5m,
		sysStatClientBytesIn5m,
		sysStatClientPktsOut5m,
		sysStatClientBytesOut5m,
		sysStatClientMaxConns5m,
		sysStatClientTotConns5m,
		sysStatClientCurConns5m,
		sysStatServerPktsIn5m,
		sysStatServerBytesIn5m,
		sysStatServerPktsOut5m,
		sysStatServerBytesOut5m,
		sysStatServerMaxConns5m,
		sysStatServerTotConns5m,
		sysStatServerCurConns5m,
		sysStatPvaClientPktsIn5s,
		sysStatPvaClientBytesIn5s,
		sysStatPvaClientPktsOut5s,
		sysStatPvaClientBytesOut5s,
		sysStatPvaClientMaxConns5s,
		sysStatPvaClientTotConns5s,
		sysStatPvaClientCurConns5s,
		sysStatPvaServerPktsIn5s,
		sysStatPvaServerBytesIn5s,
		sysStatPvaServerPktsOut5s,
		sysStatPvaServerBytesOut5s,
		sysStatPvaServerMaxConns5s,
		sysStatPvaServerTotConns5s,
		sysStatPvaServerCurConns5s,
		sysStatPvaClientPktsIn1m,
		sysStatPvaClientBytesIn1m,
		sysStatPvaClientPktsOut1m,
		sysStatPvaClientBytesOut1m,
		sysStatPvaClientMaxConns1m,
		sysStatPvaClientTotConns1m,
		sysStatPvaClientCurConns1m,
		sysStatPvaServerPktsIn1m,
		sysStatPvaServerBytesIn1m,
		sysStatPvaServerPktsOut1m,
		sysStatPvaServerBytesOut1m,
		sysStatPvaServerMaxConns1m,
		sysStatPvaServerTotConns1m,
		sysStatPvaServerCurConns1m,
		sysStatPvaClientPktsIn5m,
		sysStatPvaClientBytesIn5m,
		sysStatPvaClientPktsOut5m,
		sysStatPvaClientBytesOut5m,
		sysStatPvaClientMaxConns5m,
		sysStatPvaClientTotConns5m,
		sysStatPvaClientCurConns5m,
		sysStatPvaServerPktsIn5m,
		sysStatPvaServerBytesIn5m,
		sysStatPvaServerPktsOut5m,
		sysStatPvaServerBytesOut5m,
		sysStatPvaServerMaxConns5m,
		sysStatPvaServerTotConns5m,
		sysStatPvaServerCurConns5m,
		sysStatMemoryTotalKb,
		sysStatMemoryUsedKb
	}
	STATUS	 current
	DESCRIPTION
		"A collection of objects of sysGlobalStat MIB."
	::= { bigipSystemGroups 2 }

sysAuthStatGroup OBJECT-GROUP
	 OBJECTS {
		sysAuthStatResetStats,
		sysAuthStatTotSessions,
		sysAuthStatCurSessions,
		sysAuthStatMaxSessions,
		sysAuthStatSuccessResults,
		sysAuthStatFailureResults,
		sysAuthStatWantcredentialResults,
		sysAuthStatErrorResults
	}
	STATUS	 current
	DESCRIPTION
		"A collection of objects of sysGlobalAuthStat MIB."
	::= { bigipSystemGroups 3 }

sysConnPoolStatGroup OBJECT-GROUP
	 OBJECTS {
		sysConnPoolStatResetStats,
		sysConnPoolStatCurSize,
		sysConnPoolStatMaxSize,
		sysConnPoolStatReuses,
		sysConnPoolStatConnects
	}
	STATUS	 current
	DESCRIPTION
		"A collection of objects of sysGlobalConnPoolStat MIB."
	::= { bigipSystemGroups 4 }

sysHttpStatGroup OBJECT-GROUP
	 OBJECTS {
		sysHttpStatResetStats,
		sysHttpStatCookiePersistInserts,
		sysHttpStatResp2xxCnt,
		sysHttpStatResp3xxCnt,
		sysHttpStatResp4xxCnt,
		sysHttpStatResp5xxCnt,
		sysHttpStatNumberReqs,
		sysHttpStatGetReqs,
		sysHttpStatPostReqs,
		sysHttpStatV9Reqs,
		sysHttpStatV10Reqs,
		sysHttpStatV11Reqs,
		sysHttpStatV9Resp,
		sysHttpStatV10Resp,
		sysHttpStatV11Resp,
		sysHttpStatMaxKeepaliveReq,
		sysHttpStatRespBucket1k,
		sysHttpStatRespBucket4k,
		sysHttpStatRespBucket16k,
		sysHttpStatRespBucket32k,
		sysHttpStatPrecompressBytes,
		sysHttpStatPostcompressBytes,
		sysHttpStatNullCompressBytes,
		sysHttpStatHtmlPrecompressBytes,
		sysHttpStatHtmlPostcompressBytes,
		sysHttpStatCssPrecompressBytes,
		sysHttpStatCssPostcompressBytes,
		sysHttpStatJsPrecompressBytes,
		sysHttpStatJsPostcompressBytes,
		sysHttpStatXmlPrecompressBytes,
		sysHttpStatXmlPostcompressBytes,
		sysHttpStatSgmlPrecompressBytes,
		sysHttpStatSgmlPostcompressBytes,
		sysHttpStatPlainPrecompressBytes,
		sysHttpStatPlainPostcompressBytes,
		sysHttpStatOctetPrecompressBytes,
		sysHttpStatOctetPostcompressBytes,
		sysHttpStatImagePrecompressBytes,
		sysHttpStatImagePostcompressBytes,
		sysHttpStatVideoPrecompressBytes,
		sysHttpStatVideoPostcompressBytes,
		sysHttpStatAudioPrecompressBytes,
		sysHttpStatAudioPostcompressBytes,
		sysHttpStatOtherPrecompressBytes,
		sysHttpStatOtherPostcompressBytes,
		sysHttpStatRamcacheHits,
		sysHttpStatRamcacheMisses,
		sysHttpStatRamcacheMissesAll,
		sysHttpStatRamcacheHitBytes,
		sysHttpStatRamcacheMissBytes,
		sysHttpStatRamcacheMissBytesAll,
		sysHttpStatRamcacheSize,
		sysHttpStatRamcacheCount,
		sysHttpStatRamcacheEvictions,
		sysHttpStatRespBucket64k
	}
	STATUS	 current
	DESCRIPTION
		"A collection of objects of sysGlobalHttpStat MIB."
	::= { bigipSystemGroups 5 }

sysIcmpStatGroup OBJECT-GROUP
	 OBJECTS {
		sysIcmpStatResetStats,
		sysIcmpStatTx,
		sysIcmpStatRx,
		sysIcmpStatForward,
		sysIcmpStatDrop,
		sysIcmpStatErrCksum,
		sysIcmpStatErrLen,
		sysIcmpStatErrMem,
		sysIcmpStatErrRtx,
		sysIcmpStatErrProto,
		sysIcmpStatErrOpt,
		sysIcmpStatErr
	}
	STATUS	 current
	DESCRIPTION
		"A collection of objects of sysGlobalIcmpStat MIB."
	::= { bigipSystemGroups 6 }

sysIcmp6StatGroup OBJECT-GROUP
	 OBJECTS {
		sysIcmp6StatResetStats,
		sysIcmp6StatTx,
		sysIcmp6StatRx,
		sysIcmp6StatForward,
		sysIcmp6StatDrop,
		sysIcmp6StatErrCksum,
		sysIcmp6StatErrLen,
		sysIcmp6StatErrMem,
		sysIcmp6StatErrRtx,
		sysIcmp6StatErrProto,
		sysIcmp6StatErrOpt,
		sysIcmp6StatErr
	}
	STATUS	 current
	DESCRIPTION
		"A collection of objects of sysGlobalIcmp6Stat MIB."
	::= { bigipSystemGroups 7 }

sysIpStatGroup OBJECT-GROUP
	 OBJECTS {
		sysIpStatResetStats,
		sysIpStatTx,
		sysIpStatRx,
		sysIpStatDropped,
		sysIpStatRxFrag,
		sysIpStatRxFragDropped,
		sysIpStatTxFrag,
		sysIpStatTxFragDropped,
		sysIpStatReassembled,
		sysIpStatErrCksum,
		sysIpStatErrLen,
		sysIpStatErrMem,
		sysIpStatErrRtx,
		sysIpStatErrProto,
		sysIpStatErrOpt,
		sysIpStatErrReassembledTooLong
	}
	STATUS	 current
	DESCRIPTION
		"A collection of objects of sysGlobalIpStat MIB."
	::= { bigipSystemGroups 8 }

sysIp6StatGroup OBJECT-GROUP
	 OBJECTS {
		sysIp6StatResetStats,
		sysIp6StatTx,
		sysIp6StatRx,
		sysIp6StatDropped,
		sysIp6StatRxFrag,
		sysIp6StatRxFragDropped,
		sysIp6StatTxFrag,
		sysIp6StatTxFragDropped,
		sysIp6StatReassembled,
		sysIp6StatErrCksum,
		sysIp6StatErrLen,
		sysIp6StatErrMem,
		sysIp6StatErrRtx,
		sysIp6StatErrProto,
		sysIp6StatErrOpt,
		sysIp6StatErrReassembledTooLong
	}
	STATUS	 current
	DESCRIPTION
		"A collection of objects of sysGlobalIp6Stat MIB."
	::= { bigipSystemGroups 9 }

sysClientsslStatGroup OBJECT-GROUP
	 OBJECTS {
		sysClientsslStatResetStats,
		sysClientsslStatCurConns,
		sysClientsslStatMaxConns,
		sysClientsslStatCurNativeConns,
		sysClientsslStatMaxNativeConns,
		sysClientsslStatTotNativeConns,
		sysClientsslStatCurCompatConns,
		sysClientsslStatMaxCompatConns,
		sysClientsslStatTotCompatConns,
		sysClientsslStatEncryptedBytesIn,
		sysClientsslStatEncryptedBytesOut,
		sysClientsslStatDecryptedBytesIn,
		sysClientsslStatDecryptedBytesOut,
		sysClientsslStatRecordsIn,
		sysClientsslStatRecordsOut,
		sysClientsslStatFullyHwAcceleratedConns,
		sysClientsslStatPartiallyHwAcceleratedConns,
		sysClientsslStatNonHwAcceleratedConns,
		sysClientsslStatPrematureDisconnects,
		sysClientsslStatMidstreamRenegotiations,
		sysClientsslStatSessCacheCurEntries,
		sysClientsslStatSessCacheHits,
		sysClientsslStatSessCacheLookups,
		sysClientsslStatSessCacheOverflows,
		sysClientsslStatSessCacheInvalidations,
		sysClientsslStatPeercertValid,
		sysClientsslStatPeercertInvalid,
		sysClientsslStatPeercertNone,
		sysClientsslStatHandshakeFailures,
		sysClientsslStatBadRecords,
		sysClientsslStatFatalAlerts,
		sysClientsslStatSslv2,
		sysClientsslStatSslv3,
		sysClientsslStatTlsv1,
		sysClientsslStatAdhKeyxchg,
		sysClientsslStatDhDssKeyxchg,
		sysClientsslStatDhRsaKeyxchg,
		sysClientsslStatDssKeyxchg,
		sysClientsslStatEdhDssKeyxchg,
		sysClientsslStatRsaKeyxchg,
		sysClientsslStatNullBulk,
		sysClientsslStatAesBulk,
		sysClientsslStatDesBulk,
		sysClientsslStatIdeaBulk,
		sysClientsslStatRc2Bulk,
		sysClientsslStatRc4Bulk,
		sysClientsslStatNullDigest,
		sysClientsslStatMd5Digest,
		sysClientsslStatShaDigest,
		sysClientsslStatNotssl,
		sysClientsslStatEdhRsaKeyxchg,
		sysClientsslStatTotConns5s,
		sysClientsslStatTotConns1m,
		sysClientsslStatTotConns5m,
		sysClientsslStatSecureHandshakes,
		sysClientsslStatInsecureHandshakeAccepts,
		sysClientsslStatInsecureHandshakeRejects,
		sysClientsslStatInsecureRenegotiationRejects,
		sysClientsslStatSniRejects,
		sysClientsslStatTlsv11,
		sysClientsslStatTlsv12,
		sysClientsslStatDtlsv1,
		sysClientsslStatEcdheRsaKeyxchg,
		sysClientsslStatConns,
		sysClientsslStatCachedCerts
	}
	STATUS	 current
	DESCRIPTION
		"A collection of objects of sysGlobalClientSslStat MIB."
	::= { bigipSystemGroups 10 }

sysServersslStatGroup OBJECT-GROUP
	 OBJECTS {
		sysServersslStatResetStats,
		sysServersslStatCurConns,
		sysServersslStatMaxConns,
		sysServersslStatCurNativeConns,
		sysServersslStatMaxNativeConns,
		sysServersslStatTotNativeConns,
		sysServersslStatCurCompatConns,
		sysServersslStatMaxCompatConns,
		sysServersslStatTotCompatConns,
		sysServersslStatEncryptedBytesIn,
		sysServersslStatEncryptedBytesOut,
		sysServersslStatDecryptedBytesIn,
		sysServersslStatDecryptedBytesOut,
		sysServersslStatRecordsIn,
		sysServersslStatRecordsOut,
		sysServersslStatFullyHwAcceleratedConns,
		sysServersslStatPartiallyHwAcceleratedConns,
		sysServersslStatNonHwAcceleratedConns,
		sysServersslStatPrematureDisconnects,
		sysServersslStatMidstreamRenegotiations,
		sysServersslStatSessCacheCurEntries,
		sysServersslStatSessCacheHits,
		sysServersslStatSessCacheLookups,
		sysServersslStatSessCacheOverflows,
		sysServersslStatSessCacheInvalidations,
		sysServersslStatPeercertValid,
		sysServersslStatPeercertInvalid,
		sysServersslStatPeercertNone,
		sysServersslStatHandshakeFailures,
		sysServersslStatBadRecords,
		sysServersslStatFatalAlerts,
		sysServersslStatSslv2,
		sysServersslStatSslv3,
		sysServersslStatTlsv1,
		sysServersslStatAdhKeyxchg,
		sysServersslStatDhDssKeyxchg,
		sysServersslStatDhRsaKeyxchg,
		sysServersslStatDssKeyxchg,
		sysServersslStatEdhDssKeyxchg,
		sysServersslStatRsaKeyxchg,
		sysServersslStatNullBulk,
		sysServersslStatAesBulk,
		sysServersslStatDesBulk,
		sysServersslStatIdeaBulk,
		sysServersslStatRc2Bulk,
		sysServersslStatRc4Bulk,
		sysServersslStatNullDigest,
		sysServersslStatMd5Digest,
		sysServersslStatShaDigest,
		sysServersslStatNotssl,
		sysServersslStatEdhRsaKeyxchg,
		sysServersslStatSecureHandshakes,
		sysServersslStatInsecureHandshakeAccepts,
		sysServersslStatInsecureHandshakeRejects,
		sysServersslStatInsecureRenegotiationRejects,
		sysServersslStatSniRejects,
		sysServersslStatTlsv11,
		sysServersslStatTlsv12,
		sysServersslStatDtlsv1,
		sysServersslStatEcdheRsaKeyxchg,
		sysServersslStatConns
	}
	STATUS	 current
	DESCRIPTION
		"A collection of objects of sysGlobalServerSslStat MIB."
	::= { bigipSystemGroups 11 }

sysStreamStatGroup OBJECT-GROUP
	 OBJECTS {
		sysStreamStatResetStats,
		sysStreamStatReplaces
	}
	STATUS	 current
	DESCRIPTION
		"A collection of objects of sysGlobalStreamStat MIB."
	::= { bigipSystemGroups 12 }

sysTcpStatGroup OBJECT-GROUP
	 OBJECTS {
		sysTcpStatResetStats,
		sysTcpStatOpen,
		sysTcpStatCloseWait,
		sysTcpStatFinWait,
		sysTcpStatTimeWait,
		sysTcpStatAccepts,
		sysTcpStatAcceptfails,
		sysTcpStatConnects,
		sysTcpStatConnfails,
		sysTcpStatExpires,
		sysTcpStatAbandons,
		sysTcpStatRxrst,
		sysTcpStatRxbadsum,
		sysTcpStatRxbadseg,
		sysTcpStatRxooseg,
		sysTcpStatRxcookie,
		sysTcpStatRxbadcookie,
		sysTcpStatSyncacheover,
		sysTcpStatTxrexmits
	}
	STATUS	 current
	DESCRIPTION
		"A collection of objects of sysGlobalTcpStat MIB."
	::= { bigipSystemGroups 13 }

sysUdpStatGroup OBJECT-GROUP
	 OBJECTS {
		sysUdpStatResetStats,
		sysUdpStatOpen,
		sysUdpStatAccepts,
		sysUdpStatAcceptfails,
		sysUdpStatConnects,
		sysUdpStatConnfails,
		sysUdpStatExpires,
		sysUdpStatRxdgram,
		sysUdpStatRxbaddgram,
		sysUdpStatRxunreach,
		sysUdpStatRxbadsum,
		sysUdpStatRxnosum,
		sysUdpStatTxdgram
	}
	STATUS	 current
	DESCRIPTION
		"A collection of objects of sysGlobalUdpStat MIB."
	::= { bigipSystemGroups 14 }

sysAdminIpGroup OBJECT-GROUP
	 OBJECTS {
		sysAdminIpNumber,
		sysAdminIpAddrType,
		sysAdminIpAddr,
		sysAdminIpNetmaskType,
		sysAdminIpNetmask,
		sysAdminIpName
	}
	STATUS	 current
	DESCRIPTION
		"A collection of objects of sysAdminIp MIB."
	::= { bigipSystemGroups 15 }

sysArpStaticEntryGroup OBJECT-GROUP
	 OBJECTS {
		sysArpStaticEntryNumber,
		sysArpStaticEntryIpAddrType,
		sysArpStaticEntryIpAddr,
		sysArpStaticEntryMacAddr,
		sysArpStaticEntryName
	}
	STATUS	 current
	DESCRIPTION
		"A collection of objects of sysArpStaticEntry MIB."
	::= { bigipSystemGroups 16 }

sysDot1dbaseStatGroup OBJECT-GROUP
	 OBJECTS {
		sysDot1dbaseStatResetStats,
		sysDot1dbaseStatMacAddr,
		sysDot1dbaseStatNumPorts,
		sysDot1dbaseStatType
	}
	STATUS	 current
	DESCRIPTION
		"A collection of objects of sysDot1dbaseStat MIB."
	::= { bigipSystemGroups 17 }

sysDot1dbaseStatPortGroup OBJECT-GROUP
	 OBJECTS {
		sysDot1dbaseStatPortNumber,
		sysDot1dbaseStatPortIndex,
		sysDot1dbaseStatPortPort,
		sysDot1dbaseStatPortName,
		sysDot1dbaseStatPortDelayExceededDiscards,
		sysDot1dbaseStatPortMtuExceededDiscards
	}
	STATUS	 current
	DESCRIPTION
		"A collection of objects of sysDot1dbaseStatPort MIB."
	::= { bigipSystemGroups 18 }

sysInterfaceGroup OBJECT-GROUP
	 OBJECTS {
		sysInterfaceNumber,
		sysInterfaceName,
		sysInterfaceMediaMaxSpeed,
		sysInterfaceMediaMaxDuplex,
		sysInterfaceMediaActiveSpeed,
		sysInterfaceMediaActiveDuplex,
		sysInterfaceMacAddr,
		sysInterfaceMtu,
		sysInterfaceEnabled,
		sysInterfaceLearnMode,
		sysInterfaceFlowCtrlReq,
		sysInterfaceStpLink,
		sysInterfaceStpEdge,
		sysInterfaceStpEdgeActive,
		sysInterfaceStpAuto,
		sysInterfaceStpEnable,
		sysInterfaceStpReset,
		sysInterfaceStatus,
		sysInterfaceComboPort,
		sysInterfacePreferSfp,
		sysInterfaceSfpMedia,
		sysInterfacePhyMaster
	}
	STATUS	 current
	DESCRIPTION
		"A collection of objects of sysInterface MIB."
	::= { bigipSystemGroups 19 }

sysIntfMediaGroup OBJECT-GROUP
	 OBJECTS {
		sysIntfMediaNumber,
		sysIntfMediaName,
		sysIntfMediaIndex,
		sysIntfMediaMediaOption
	}
	STATUS	 current
	DESCRIPTION
		"A collection of objects of sysInterfaceMediaOptions MIB."
	::= { bigipSystemGroups 20 }

sysIfGroup OBJECT-GROUP
	 OBJECTS {
		sysIfNumber,
		sysIfIndex,
		sysIfName
	}
	STATUS	 current
	DESCRIPTION
		"A collection of objects of sysInterfaceId MIB."
	::= { bigipSystemGroups 21 }

sysInterfaceStatGroup OBJECT-GROUP
	 OBJECTS {
		sysInterfaceStatResetStats,
		sysInterfaceStatNumber,
		sysInterfaceStatName,
		sysInterfaceStatPktsIn,
		sysInterfaceStatBytesIn,
		sysInterfaceStatPktsOut,
		sysInterfaceStatBytesOut,
		sysInterfaceStatMcastIn,
		sysInterfaceStatMcastOut,
		sysInterfaceStatErrorsIn,
		sysInterfaceStatErrorsOut,
		sysInterfaceStatDropsIn,
		sysInterfaceStatDropsOut,
		sysInterfaceStatCollisions,
		sysInterfaceStatPauseActive
	}
	STATUS	 current
	DESCRIPTION
		"A collection of objects of sysInterfaceStat MIB."
	::= { bigipSystemGroups 22 }

sysIfxStatGroup OBJECT-GROUP
	 OBJECTS {
		sysIfxStatResetStats,
		sysIfxStatNumber,
		sysIfxStatName,
		sysIfxStatInMulticastPkts,
		sysIfxStatInBroadcastPkts,
		sysIfxStatOutMulticastPkts,
		sysIfxStatOutBroadcastPkts,
		sysIfxStatHcInOctets,
		sysIfxStatHcInUcastPkts,
		sysIfxStatHcInMulticastPkts,
		sysIfxStatHcInBroadcastPkts,
		sysIfxStatHcOutOctets,
		sysIfxStatHcOutUcastPkts,
		sysIfxStatHcOutMulticastPkts,
		sysIfxStatHcOutBroadcastPkts,
		sysIfxStatHighSpeed,
		sysIfxStatConnectorPresent,
		sysIfxStatCounterDiscontinuityTime,
		sysIfxStatAlias
	}
	STATUS	 current
	DESCRIPTION
		"A collection of objects of sysIfxStat MIB."
	::= { bigipSystemGroups 23 }

sysL2ForwardGroup OBJECT-GROUP
	 OBJECTS {
		sysL2ForwardNumber,
		sysL2ForwardVlanName,
		sysL2ForwardMacAddr,
		sysL2ForwardIfname,
		sysL2ForwardIftype,
		sysL2ForwardDynamic
	}
	STATUS	 current
	DESCRIPTION
		"A collection of objects of sysL2Forward MIB."
	::= { bigipSystemGroups 24 }

sysPacketFilterGroup OBJECT-GROUP
	 OBJECTS {
		sysPacketFilterNumber,
		sysPacketFilterRname,
		sysPacketFilterOrder,
		sysPacketFilterAction,
		sysPacketFilterVname,
		sysPacketFilterLog,
		sysPacketFilterRclass,
		sysPacketFilterExpression
	}
	STATUS	 current
	DESCRIPTION
		"A collection of objects of sysPacketFilter MIB."
	::= { bigipSystemGroups 25 }

sysPacketFilterAddrGroup OBJECT-GROUP
	 OBJECTS {
		sysPacketFilterAddrNumber,
		sysPacketFilterAddrIndex,
		sysPacketFilterAddrIpType,
		sysPacketFilterAddrIp,
		sysPacketFilterAddrRname
	}
	STATUS	 current
	DESCRIPTION
		"A collection of objects of sysPacketFilterAddress MIB."
	::= { bigipSystemGroups 26 }

sysPacketFilterVlanGroup OBJECT-GROUP
	 OBJECTS {
		sysPacketFilterVlanNumber,
		sysPacketFilterVlanIndex,
		sysPacketFilterVlanName,
		sysPacketFilterVlanRname
	}
	STATUS	 current
	DESCRIPTION
		"A collection of objects of sysPacketFilterVlan MIB."
	::= { bigipSystemGroups 27 }

sysPacketFilterMacGroup OBJECT-GROUP
	 OBJECTS {
		sysPacketFilterMacNumber,
		sysPacketFilterMacIndex,
		sysPacketFilterMacAddr,
		sysPacketFilterMacRname
	}
	STATUS	 current
	DESCRIPTION
		"A collection of objects of sysPacketFilterMac MIB."
	::= { bigipSystemGroups 28 }

sysPacketFilterStatGroup OBJECT-GROUP
	 OBJECTS {
		sysPacketFilterStatResetStats,
		sysPacketFilterStatNumber,
		sysPacketFilterStatRname,
		sysPacketFilterStatHits
	}
	STATUS	 current
	DESCRIPTION
		"A collection of objects of sysPacketFilterStat MIB."
	::= { bigipSystemGroups 29 }

sysRouteMgmtEntryGroup OBJECT-GROUP
	 OBJECTS {
		sysRouteMgmtEntryNumber,
		sysRouteMgmtEntryDestType,
		sysRouteMgmtEntryDest,
		sysRouteMgmtEntryNetmaskType,
		sysRouteMgmtEntryNetmask,
		sysRouteMgmtEntryType,
		sysRouteMgmtEntryGatewayType,
		sysRouteMgmtEntryGateway,
		sysRouteMgmtEntryMtu,
		sysRouteMgmtEntryName
	}
	STATUS	 current
	DESCRIPTION
		"A collection of objects of sysRouteMgmtEntry MIB."
	::= { bigipSystemGroups 30 }

sysRouteStaticEntryGroup OBJECT-GROUP
	 OBJECTS {
		sysRouteStaticEntryNumber,
		sysRouteStaticEntryDestType,
		sysRouteStaticEntryDest,
		sysRouteStaticEntryNetmaskType,
		sysRouteStaticEntryNetmask,
		sysRouteStaticEntryType,
		sysRouteStaticEntryVlanName,
		sysRouteStaticEntryGatewayType,
		sysRouteStaticEntryGateway,
		sysRouteStaticEntryPoolName,
		sysRouteStaticEntryMtu,
		sysRouteStaticEntryName
	}
	STATUS	 current
	DESCRIPTION
		"A collection of objects of sysRouteStaticEntry MIB."
	::= { bigipSystemGroups 31 }

sysSelfIpGroup OBJECT-GROUP
	 OBJECTS {
		sysSelfIpNumber,
		sysSelfIpAddrType,
		sysSelfIpAddr,
		sysSelfIpNetmaskType,
		sysSelfIpNetmask,
		sysSelfIpUnitId,
		sysSelfIpIsFloating,
		sysSelfIpVlanName,
		sysSelfIpName
	}
	STATUS	 current
	DESCRIPTION
		"A collection of objects of sysSelfIp MIB."
	::= { bigipSystemGroups 32 }

sysSelfPortGroup OBJECT-GROUP
	 OBJECTS {
		sysSelfPortNumber,
		sysSelfPortAddrType,
		sysSelfPortAddr,
		sysSelfPortProtocol,
		sysSelfPortPort,
		sysSelfPortSelfName
	}
	STATUS	 current
	DESCRIPTION
		"A collection of objects of sysSelfPort MIB."
	::= { bigipSystemGroups 33 }

sysStpGroup OBJECT-GROUP
	 OBJECTS {
		sysStpNumber,
		sysStpInstanceId,
		sysStpPriority,
		sysStpRootAddr,
		sysStpRegionalRootAddr,
		sysStpName
	}
	STATUS	 current
	DESCRIPTION
		"A collection of objects of sysStp MIB."
	::= { bigipSystemGroups 34 }

sysStpGlobalsGroup OBJECT-GROUP
	 OBJECTS {
		sysStpGlobalsMode,
		sysStpGlobalsFwdDelay,
		sysStpGlobalsHelloTime,
		sysStpGlobalsMaxAge,
		sysStpGlobalsTransmitHold,
		sysStpGlobalsMaxHops,
		sysStpGlobalsIdentifier,
		sysStpGlobalsRevision
	}
	STATUS	 current
	DESCRIPTION
		"A collection of objects of sysStpGlobals MIB."
	::= { bigipSystemGroups 35 }

sysStpInterfaceMbrGroup OBJECT-GROUP
	 OBJECTS {
		sysStpInterfaceMbrNumber,
		sysStpInterfaceMbrInstanceId,
		sysStpInterfaceMbrName,
		sysStpInterfaceMbrType,
		sysStpInterfaceMbrStateActive,
		sysStpInterfaceMbrRole,
		sysStpInterfaceMbrPriority,
		sysStpInterfaceMbrPathCost,
		sysStpInterfaceMbrStateRequested,
		sysStpInterfaceMbrInstanceName
	}
	STATUS	 current
	DESCRIPTION
		"A collection of objects of sysStpInterfaceMbr MIB."
	::= { bigipSystemGroups 36 }

sysStpVlanMbrGroup OBJECT-GROUP
	 OBJECTS {
		sysStpVlanMbrNumber,
		sysStpVlanMbrInstanceId,
		sysStpVlanMbrVlanVname,
		sysStpVlanMbrStpName
	}
	STATUS	 current
	DESCRIPTION
		"A collection of objects of sysStpVlanMbr MIB."
	::= { bigipSystemGroups 37 }

sysStpBridgeStatGroup OBJECT-GROUP
	 OBJECTS {
		sysStpBridgeStatResetStats,
		sysStpBridgeStatMode,
		sysStpBridgeStatFwdDelay,
		sysStpBridgeStatHelloTime,
		sysStpBridgeStatMaxAge,
		sysStpBridgeStatBridgeFwdDelay,
		sysStpBridgeStatBridgeHelloTime,
		sysStpBridgeStatBridgeMaxAge,
		sysStpBridgeStatTransmitHold,
		sysStpBridgeStatPathCost,
		sysStpBridgeStatRootPrio,
		sysStpBridgeStatRootAddr
	}
	STATUS	 current
	DESCRIPTION
		"A collection of objects of sysStpBridgeStat MIB."
	::= { bigipSystemGroups 38 }

sysStpBridgeTreeStatGroup OBJECT-GROUP
	 OBJECTS {
		sysStpBridgeTreeStatNumber,
		sysStpBridgeTreeStatIndex,
		sysStpBridgeTreeStatInstanceId,
		sysStpBridgeTreeStatPriority,
		sysStpBridgeTreeStatLastTc,
		sysStpBridgeTreeStatTcCount,
		sysStpBridgeTreeStatDesigRootPrio,
		sysStpBridgeTreeStatDesigRootAddr,
		sysStpBridgeTreeStatInternalPathCost,
		sysStpBridgeTreeStatRootPort,
		sysStpBridgeTreeStatRootPortNum,
		sysStpBridgeTreeStatInstanceName
	}
	STATUS	 current
	DESCRIPTION
		"A collection of objects of sysStpBridgeTreeStat MIB."
	::= { bigipSystemGroups 39 }

sysStpInterfaceStatGroup OBJECT-GROUP
	 OBJECTS {
		sysStpInterfaceStatResetStats,
		sysStpInterfaceStatNumber,
		sysStpInterfaceStatName,
		sysStpInterfaceStatPortNum,
		sysStpInterfaceStatStpEnable,
		sysStpInterfaceStatPathCost,
		sysStpInterfaceStatRootCost,
		sysStpInterfaceStatRootPrio,
		sysStpInterfaceStatRootAddr
	}
	STATUS	 current
	DESCRIPTION
		"A collection of objects of sysStpInterfaceStat MIB."
	::= { bigipSystemGroups 40 }

sysStpInterfaceTreeStatGroup OBJECT-GROUP
	 OBJECTS {
		sysStpInterfaceTreeStatNumber,
		sysStpInterfaceTreeStatName,
		sysStpInterfaceTreeStatIndex,
		sysStpInterfaceTreeStatInstanceId,
		sysStpInterfaceTreeStatPriority,
		sysStpInterfaceTreeStatState,
		sysStpInterfaceTreeStatStatRole,
		sysStpInterfaceTreeStatDesigRootPrio,
		sysStpInterfaceTreeStatDesigRootAddr,
		sysStpInterfaceTreeStatDesigCost,
		sysStpInterfaceTreeStatDesigBridgePrio,
		sysStpInterfaceTreeStatDesigBridgeAddr,
		sysStpInterfaceTreeStatDesigPortNum,
		sysStpInterfaceTreeStatDesigPortPriority,
		sysStpInterfaceTreeStatInternalPathCost,
		sysStpInterfaceTreeStatFwdTransitions
	}
	STATUS	 current
	DESCRIPTION
		"A collection of objects of sysStpInterfaceTreeStat MIB."
	::= { bigipSystemGroups 41 }

sysDot3StatGroup OBJECT-GROUP
	 OBJECTS {
		sysDot3StatResetStats,
		sysDot3StatNumber,
		sysDot3StatName,
		sysDot3StatAlignmentErrors,
		sysDot3StatFcsErrors,
		sysDot3StatSingleCollisionFrames,
		sysDot3StatMultiCollisionFrames,
		sysDot3StatSqetestErrors,
		sysDot3StatDeferredTx,
		sysDot3StatLateCollisions,
		sysDot3StatExcessiveCollisions,
		sysDot3StatIntmacTxErrors,
		sysDot3StatCarrierSenseErrors,
		sysDot3StatFrameTooLongs,
		sysDot3StatIntmacRxErrors,
		sysDot3StatSymbolErrors,
		sysDot3StatDuplexStatus,
		sysDot3StatCollisionCount,
		sysDot3StatCollisionFreq
	}
	STATUS	 current
	DESCRIPTION
		"A collection of objects of sysDot3Stat MIB."
	::= { bigipSystemGroups 42 }

sysTrunkGroup OBJECT-GROUP
	 OBJECTS {
		sysTrunkNumber,
		sysTrunkName,
		sysTrunkStatus,
		sysTrunkAggAddr,
		sysTrunkCfgMbrCount,
		sysTrunkOperBw,
		sysTrunkStpEnable,
		sysTrunkStpReset,
		sysTrunkLacpEnabled,
		sysTrunkActiveLacp,
		sysTrunkShortTimeout
	}
	STATUS	 current
	DESCRIPTION
		"A collection of objects of sysTrunk MIB."
	::= { bigipSystemGroups 43 }

sysTrunkStatGroup OBJECT-GROUP
	 OBJECTS {
		sysTrunkStatResetStats,
		sysTrunkStatNumber,
		sysTrunkStatName,
		sysTrunkStatPktsIn,
		sysTrunkStatBytesIn,
		sysTrunkStatPktsOut,
		sysTrunkStatBytesOut,
		sysTrunkStatMcastIn,
		sysTrunkStatMcastOut,
		sysTrunkStatErrorsIn,
		sysTrunkStatErrorsOut,
		sysTrunkStatDropsIn,
		sysTrunkStatDropsOut,
		sysTrunkStatCollisions
	}
	STATUS	 current
	DESCRIPTION
		"A collection of objects of sysTrunkStat MIB."
	::= { bigipSystemGroups 44 }

sysTrunkCfgMemberGroup OBJECT-GROUP
	 OBJECTS {
		sysTrunkCfgMemberNumber,
		sysTrunkCfgMemberTrunkName,
		sysTrunkCfgMemberName
	}
	STATUS	 current
	DESCRIPTION
		"A collection of objects of sysTrunkCfgMember MIB."
	::= { bigipSystemGroups 45 }

sysVlanDataGroup OBJECT-GROUP
	 OBJECTS {
		sysVlanNumber,
		sysVlanVname,
		sysVlanId,
		sysVlanSpanningTree,
		sysVlanMacMasquerade,
		sysVlanMacTrue,
		sysVlanSourceCheck,
		sysVlanFailsafeEnabled,
		sysVlanMtu,
		sysVlanFailsafeTimeout,
		sysVlanFailsafeAction,
		sysVlanMirrorHashPortEnable,
		sysVlanLearnMode
	}
	STATUS	 current
	DESCRIPTION
		"A collection of objects of sysVlan MIB."
	::= { bigipSystemGroups 46 }

sysVlanMemberGroup OBJECT-GROUP
	 OBJECTS {
		sysVlanMemberNumber,
		sysVlanMemberVmname,
		sysVlanMemberParentVname,
		sysVlanMemberTagged,
		sysVlanMemberType
	}
	STATUS	 current
	DESCRIPTION
		"A collection of objects of sysVlanMember MIB."
	::= { bigipSystemGroups 47 }

sysVlanGroupGroup OBJECT-GROUP
	 OBJECTS {
		sysVlanGroupNumber,
		sysVlanGroupName,
		sysVlanGroupVlanId,
		sysVlanGroupMode,
		sysVlanGroupBridgeAllTraffic,
		sysVlanGroupBridgeInStandby,
		sysVlanGroupBridgeMulticast,
		sysVlanGroupMacMasquerade,
		sysVlanGroupMacTrue
	}
	STATUS	 current
	DESCRIPTION
		"A collection of objects of sysVlanGroup MIB."
	::= { bigipSystemGroups 48 }

sysVlanGroupMbrGroup OBJECT-GROUP
	 OBJECTS {
		sysVlanGroupMbrNumber,
		sysVlanGroupMbrGroupName,
		sysVlanGroupMbrVlanName
	}
	STATUS	 current
	DESCRIPTION
		"A collection of objects of sysVlanGroupMbr MIB."
	::= { bigipSystemGroups 49 }

sysProxyExclusionGroup OBJECT-GROUP
	 OBJECTS {
		sysProxyExclusionNumber,
		sysProxyExclusionVlangroupName,
		sysProxyExclusionIpType,
		sysProxyExclusionIp
	}
	STATUS	 current
	DESCRIPTION
		"A collection of objects of sysProxyExclusion MIB."
	::= { bigipSystemGroups 50 }

sysCpuGroup OBJECT-GROUP
	 OBJECTS {
		sysCpuNumber,
		sysCpuIndex,
		sysCpuTemperature,
		sysCpuFanSpeed,
		sysCpuName,
		sysCpuSlot
	}
	STATUS	 current
	DESCRIPTION
		"A collection of objects of sysCpu MIB."
	::= { bigipSystemGroups 51 }

sysChassisFanGroup OBJECT-GROUP
	 OBJECTS {
		sysChassisFanNumber,
		sysChassisFanIndex,
		sysChassisFanStatus,
		sysChassisFanSpeed
	}
	STATUS	 current
	DESCRIPTION
		"A collection of objects of sysChassisFan MIB."
	::= { bigipSystemGroups 52 }

sysChassisPowerSupplyGroup OBJECT-GROUP
	 OBJECTS {
		sysChassisPowerSupplyNumber,
		sysChassisPowerSupplyIndex,
		sysChassisPowerSupplyStatus
	}
	STATUS	 current
	DESCRIPTION
		"A collection of objects of sysChassisPowerSupply MIB."
	::= { bigipSystemGroups 53 }

sysChassisTempGroup OBJECT-GROUP
	 OBJECTS {
		sysChassisTempNumber,
		sysChassisTempIndex,
		sysChassisTempTemperature
	}
	STATUS	 current
	DESCRIPTION
		"A collection of objects of sysChassisTemp MIB."
	::= { bigipSystemGroups 54 }

sysProductGroup OBJECT-GROUP
	 OBJECTS {
		sysProductName,
		sysProductVersion,
		sysProductBuild,
		sysProductEdition,
		sysProductDate,
		sysProductHotfix
	}
	STATUS	 current
	DESCRIPTION
		"A collection of objects of sysProduct MIB."
	::= { bigipSystemGroups 55 }

sysSubMemoryGroup OBJECT-GROUP
	 OBJECTS {
		sysSubMemoryResetStats,
		sysSubMemoryNumber,
		sysSubMemoryName,
		sysSubMemoryAllocated,
		sysSubMemoryMaxAllocated,
		sysSubMemorySize
	}
	STATUS	 current
	DESCRIPTION
		"A collection of objects of sysSubMemory MIB."
	::= { bigipSystemGroups 56 }

sysSystemGroup OBJECT-GROUP
	 OBJECTS {
		sysSystemName,
		sysSystemNodeName,
		sysSystemRelease,
		sysSystemVersion,
		sysSystemMachine,
		sysSystemUptime,
		sysSystemUptimeInSec
	}
	STATUS	 current
	DESCRIPTION
		"A collection of objects of sysSystem MIB."
	::= { bigipSystemGroups 57 }

sysFastHttpStatGroup OBJECT-GROUP
	 OBJECTS {
		sysFastHttpStatResetStats,
		sysFastHttpStatClientSyns,
		sysFastHttpStatClientAccepts,
		sysFastHttpStatServerConnects,
		sysFastHttpStatConnpoolCurSize,
		sysFastHttpStatConnpoolMaxSize,
		sysFastHttpStatConnpoolReuses,
		sysFastHttpStatConnpoolExhausted,
		sysFastHttpStatNumberReqs,
		sysFastHttpStatUnbufferedReqs,
		sysFastHttpStatGetReqs,
		sysFastHttpStatPostReqs,
		sysFastHttpStatV9Reqs,
		sysFastHttpStatV10Reqs,
		sysFastHttpStatV11Reqs,
		sysFastHttpStatResp2xxCnt,
		sysFastHttpStatResp3xxCnt,
		sysFastHttpStatResp4xxCnt,
		sysFastHttpStatResp5xxCnt,
		sysFastHttpStatReqParseErrors,
		sysFastHttpStatRespParseErrors,
		sysFastHttpStatClientRxBad,
		sysFastHttpStatServerRxBad,
		sysFastHttpStatPipelinedReqs
	}
	STATUS	 current
	DESCRIPTION
		"A collection of objects of sysGlobalFastHttpStat MIB."
	::= { bigipSystemGroups 58 }

sysXmlStatGroup OBJECT-GROUP
	 OBJECTS {
		sysXmlStatResetStats,
		sysXmlStatNumErrors
	}
	STATUS	 current
	DESCRIPTION
		"A collection of objects of sysGlobalXmlStat MIB."
	::= { bigipSystemGroups 59 }

sysGeneralGroup OBJECT-GROUP
	 OBJECTS {
		sysGeneralHwName,
		sysGeneralHwNumber,
		sysGeneralChassisSerialNum
	}
	STATUS	 current
	DESCRIPTION
		"A collection of objects of sysGeneral MIB."
	::= { bigipSystemGroups 60 }

sysIiopStatGroup OBJECT-GROUP
	 OBJECTS {
		sysIiopStatResetStats,
		sysIiopStatNumRequests,
		sysIiopStatNumResponses,
		sysIiopStatNumCancels,
		sysIiopStatNumErrors,
		sysIiopStatNumFragments
	}
	STATUS	 current
	DESCRIPTION
		"A collection of objects of sysGlobalIiopStat MIB."
	::= { bigipSystemGroups 61 }

sysRtspStatGroup OBJECT-GROUP
	 OBJECTS {
		sysRtspStatResetStats,
		sysRtspStatNumRequests,
		sysRtspStatNumResponses,
		sysRtspStatNumErrors,
		sysRtspStatNumInterleavedData
	}
	STATUS	 current
	DESCRIPTION
		"A collection of objects of sysGlobalRtspStat MIB."
	::= { bigipSystemGroups 62 }

sysSctpStatGroup OBJECT-GROUP
	 OBJECTS {
		sysSctpStatResetStats,
		sysSctpStatAccepts,
		sysSctpStatAcceptfails,
		sysSctpStatConnects,
		sysSctpStatConnfails,
		sysSctpStatExpires,
		sysSctpStatAbandons,
		sysSctpStatRxrst,
		sysSctpStatRxbadsum,
		sysSctpStatRxcookie,
		sysSctpStatRxbadcookie
	}
	STATUS	 current
	DESCRIPTION
		"A collection of objects of sysGlobalSctpStat MIB."
	::= { bigipSystemGroups 63 }

sysL2ForwardStatGroup OBJECT-GROUP
	 OBJECTS {
		sysL2ForwardStatNumber,
		sysL2ForwardStatVlanName,
		sysL2ForwardStatMacAddr,
		sysL2ForwardStatIfname,
		sysL2ForwardStatIftype,
		sysL2ForwardStatDynamic
	}
	STATUS	 current
	DESCRIPTION
		"A collection of objects of sysL2ForwardStat MIB."
	::= { bigipSystemGroups 64 }

sysL2ForwardAttrGroup OBJECT-GROUP
	 OBJECTS {
		sysL2ForwardAttrVlan
	}
	STATUS	 current
	DESCRIPTION
		"A collection of objects of sysL2ForwardAttr MIB."
	::= { bigipSystemGroups 65 }

sysHostMemoryGroup OBJECT-GROUP
	 OBJECTS {
		sysHostMemoryTotal,
		sysHostMemoryUsed
	}
	STATUS	 current
	DESCRIPTION
		"A collection of objects of sysHostMemory MIB."
	::= { bigipSystemGroups 66 }

sysHostCpuGroup OBJECT-GROUP
	 OBJECTS {
		sysHostCpuNumber,
		sysHostCpuIndex,
		sysHostCpuId,
		sysHostCpuUser,
		sysHostCpuNice,
		sysHostCpuSystem,
		sysHostCpuIdle,
		sysHostCpuIrq,
		sysHostCpuSoftirq,
		sysHostCpuIowait
	}
	STATUS	 current
	DESCRIPTION
		"A collection of objects of sysHostCpu MIB."
	::= { bigipSystemGroups 67 }

sysHostDiskGroup OBJECT-GROUP
	 OBJECTS {
		sysHostDiskNumber,
		sysHostDiskPartition,
		sysHostDiskBlockSize,
		sysHostDiskTotalBlocks,
		sysHostDiskFreeBlocks,
		sysHostDiskTotalNodes,
		sysHostDiskFreeNodes
	}
	STATUS	 current
	DESCRIPTION
		"A collection of objects of sysHostDisk MIB."
	::= { bigipSystemGroups 68 }

sysSelfPortDefGroup OBJECT-GROUP
	 OBJECTS {
		sysSelfPortDefNumber,
		sysSelfPortDefProtocol,
		sysSelfPortDefPort,
		sysSelfPortDefAllowName
	}
	STATUS	 current
	DESCRIPTION
		"A collection of objects of sysSelfPortDefault MIB."
	::= { bigipSystemGroups 69 }

sysIntfMediaSfpGroup OBJECT-GROUP
	 OBJECTS {
		sysIntfMediaSfpNumber,
		sysIntfMediaSfpName,
		sysIntfMediaSfpIndex,
		sysIntfMediaSfpType
	}
	STATUS	 current
	DESCRIPTION
		"A collection of objects of sysInterfaceMediaSfp MIB."
	::= { bigipSystemGroups 70 }

sysPvaStatGroup OBJECT-GROUP
	 OBJECTS {
		sysPvaStatResetStats,
		sysPvaStatNumber,
		sysPvaStatPvaId,
		sysPvaStatClientPktsIn,
		sysPvaStatClientBytesIn,
		sysPvaStatClientPktsOut,
		sysPvaStatClientBytesOut,
		sysPvaStatClientMaxConns,
		sysPvaStatClientTotConns,
		sysPvaStatClientCurConns,
		sysPvaStatServerPktsIn,
		sysPvaStatServerBytesIn,
		sysPvaStatServerPktsOut,
		sysPvaStatServerBytesOut,
		sysPvaStatServerMaxConns,
		sysPvaStatServerTotConns,
		sysPvaStatServerCurConns,
		sysPvaStatTotAssistConns,
		sysPvaStatCurAssistConns,
		sysPvaStatHardSyncookieGen,
		sysPvaStatHardSyncookieDet
	}
	STATUS	 current
	DESCRIPTION
		"A collection of objects of sysPvaStat MIB."
	::= { bigipSystemGroups 71 }

sysTmmStatGroup OBJECT-GROUP
	 OBJECTS {
		sysTmmStatResetStats,
		sysTmmStatNumber,
		sysTmmStatTmmId,
		sysTmmStatTmmPid,
		sysTmmStatCpu,
		sysTmmStatTmid,
		sysTmmStatNpus,
		sysTmmStatClientPktsIn,
		sysTmmStatClientBytesIn,
		sysTmmStatClientPktsOut,
		sysTmmStatClientBytesOut,
		sysTmmStatClientMaxConns,
		sysTmmStatClientTotConns,
		sysTmmStatClientCurConns,
		sysTmmStatServerPktsIn,
		sysTmmStatServerBytesIn,
		sysTmmStatServerPktsOut,
		sysTmmStatServerBytesOut,
		sysTmmStatServerMaxConns,
		sysTmmStatServerTotConns,
		sysTmmStatServerCurConns,
		sysTmmStatMaintenanceModeDeny,
		sysTmmStatMaxConnVirtualAddrDeny,
		sysTmmStatMaxConnVirtualPathDeny,
		sysTmmStatVirtualServerNonSynDeny,
		sysTmmStatNoHandlerDeny,
		sysTmmStatLicenseDeny,
		sysTmmStatCmpConnRedirected,
		sysTmmStatConnectionMemoryErrors,
		sysTmmStatTmTotalCycles,
		sysTmmStatTmIdleCycles,
		sysTmmStatTmSleepCycles,
		sysTmmStatMemoryTotal,
		sysTmmStatMemoryUsed,
		sysTmmStatDroppedPackets,
		sysTmmStatIncomingPacketErrors,
		sysTmmStatOutgoingPacketErrors,
		sysTmmStatHttpRequests,
		sysTmmStatTmUsageRatio5s,
		sysTmmStatTmUsageRatio1m,
		sysTmmStatTmUsageRatio5m,
		sysTmmStatSlotId,
		sysTmmStatMemoryTotalKb,
		sysTmmStatMemoryUsedKb
	}
	STATUS	 current
	DESCRIPTION
		"A collection of objects of sysTmmStat MIB."
	::= { bigipSystemGroups 72 }

sysMultiHostGroup OBJECT-GROUP
	 OBJECTS {
		sysMultiHostNumber,
		sysMultiHostHostId,
		sysMultiHostTotal,
		sysMultiHostUsed,
		sysMultiHostMode,
		sysMultiHostCpuCount,
		sysMultiHostActiveCpuCount
	}
	STATUS	 current
	DESCRIPTION
		"A collection of objects of sysMultiHost MIB."
	::= { bigipSystemGroups 73 }

sysMultiHostCpuGroup OBJECT-GROUP
	 OBJECTS {
		sysMultiHostCpuNumber,
		sysMultiHostCpuHostId,
		sysMultiHostCpuIndex,
		sysMultiHostCpuId,
		sysMultiHostCpuUser,
		sysMultiHostCpuNice,
		sysMultiHostCpuSystem,
		sysMultiHostCpuIdle,
		sysMultiHostCpuIrq,
		sysMultiHostCpuSoftirq,
		sysMultiHostCpuIowait,
		sysMultiHostCpuUsageRatio,
		sysMultiHostCpuUser5s,
		sysMultiHostCpuNice5s,
		sysMultiHostCpuSystem5s,
		sysMultiHostCpuIdle5s,
		sysMultiHostCpuIrq5s,
		sysMultiHostCpuSoftirq5s,
		sysMultiHostCpuIowait5s,
		sysMultiHostCpuUsageRatio5s,
		sysMultiHostCpuUser1m,
		sysMultiHostCpuNice1m,
		sysMultiHostCpuSystem1m,
		sysMultiHostCpuIdle1m,
		sysMultiHostCpuIrq1m,
		sysMultiHostCpuSoftirq1m,
		sysMultiHostCpuIowait1m,
		sysMultiHostCpuUsageRatio1m,
		sysMultiHostCpuUser5m,
		sysMultiHostCpuNice5m,
		sysMultiHostCpuSystem5m,
		sysMultiHostCpuIdle5m,
		sysMultiHostCpuIrq5m,
		sysMultiHostCpuSoftirq5m,
		sysMultiHostCpuIowait5m,
		sysMultiHostCpuUsageRatio5m,
		sysMultiHostCpuStolen,
		sysMultiHostCpuStolen5s,
		sysMultiHostCpuStolen1m,
		sysMultiHostCpuStolen5m,
		sysMultiHostCpuSlotId
	}
	STATUS	 current
	DESCRIPTION
		"A collection of objects of sysMultiHostCpu MIB."
	::= { bigipSystemGroups 74 }

sysFastL4StatGroup OBJECT-GROUP
	 OBJECTS {
		sysFastL4StatResetStats,
		sysFastL4StatOpen,
		sysFastL4StatAccepts,
		sysFastL4StatAcceptfails,
		sysFastL4StatExpires,
		sysFastL4StatRxbadpkt,
		sysFastL4StatRxunreach,
		sysFastL4StatRxbadunreach,
		sysFastL4StatRxbadsum,
		sysFastL4StatTxerrors,
		sysFastL4StatSyncookIssue,
		sysFastL4StatSyncookAccept,
		sysFastL4StatSyncookReject,
		sysFastL4StatServersynrtx
	}
	STATUS	 current
	DESCRIPTION
		"A collection of objects of sysGlobalFastL4Stat MIB."
	::= { bigipSystemGroups 75 }

sysClusterGroup OBJECT-GROUP
	 OBJECTS {
		sysClusterNumber,
		sysClusterName,
		sysClusterEnabled,
		sysClusterFloatMgmtIpType,
		sysClusterFloatMgmtIp,
		sysClusterFloatMgmtNetmaskType,
		sysClusterFloatMgmtNetmask,
		sysClusterMinUpMbrs,
		sysClusterMinUpMbrsEnable,
		sysClusterMinUpMbrsAction,
		sysClusterAvailabilityState,
		sysClusterEnabledStat,
		sysClusterDisabledParentType,
		sysClusterStatusReason,
		sysClusterHaState,
		sysClusterPriSlotId,
		sysClusterLastPriSlotId,
		sysClusterPriSelTime
	}
	STATUS	 current
	DESCRIPTION
		"A collection of objects of sysCluster MIB."
	::= { bigipSystemGroups 76 }

sysClusterMbrGroup OBJECT-GROUP
	 OBJECTS {
		sysClusterMbrNumber,
		sysClusterMbrCluster,
		sysClusterMbrSlotId,
		sysClusterMbrAvailabilityState,
		sysClusterMbrEnabledStat,
		sysClusterMbrDisabledParentType,
		sysClusterMbrStatusReason,
		sysClusterMbrLicensed,
		sysClusterMbrState,
		sysClusterMbrEnabled,
		sysClusterMbrPriming,
		sysClusterMbrMgmtAddrType,
		sysClusterMbrMgmtAddr,
		sysClusterMbrHaState
	}
	STATUS	 current
	DESCRIPTION
		"A collection of objects of sysClusterMbr MIB."
	::= { bigipSystemGroups 77 }

sysSwVolumeGroup OBJECT-GROUP
	 OBJECTS {
		sysSwVolumeNumber,
		sysSwVolumeSlotId,
		sysSwVolumeName,
		sysSwVolumeSize,
		sysSwVolumeActive
	}
	STATUS	 current
	DESCRIPTION
		"A collection of objects of sysSoftwareVolume MIB."
	::= { bigipSystemGroups 78 }

sysSwImageGroup OBJECT-GROUP
	 OBJECTS {
		sysSwImageNumber,
		sysSwImageSlotId,
		sysSwImageFilename,
		sysSwImageProduct,
		sysSwImageVersion,
		sysSwImageBuild,
		sysSwImageChksum,
		sysSwImageVerified,
		sysSwImageBuildDate,
		sysSwImageLastModified,
		sysSwImageFileSize
	}
	STATUS	 current
	DESCRIPTION
		"A collection of objects of sysSoftwareImage MIB."
	::= { bigipSystemGroups 79 }

sysSwHotfixGroup OBJECT-GROUP
	 OBJECTS {
		sysSwHotfixNumber,
		sysSwHotfixSlotId,
		sysSwHotfixFilename,
		sysSwHotfixProduct,
		sysSwHotfixVersion,
		sysSwHotfixBuild,
		sysSwHotfixChksum,
		sysSwHotfixVerified,
		sysSwHotfixHotfixId,
		sysSwHotfixHotfixTitle
	}
	STATUS	 current
	DESCRIPTION
		"A collection of objects of sysSoftwareHotfix MIB."
	::= { bigipSystemGroups 80 }

sysSwStatusGroup OBJECT-GROUP
	 OBJECTS {
		sysSwStatusNumber,
		sysSwStatusSlotId,
		sysSwStatusVolume,
		sysSwStatusProduct,
		sysSwStatusVersion,
		sysSwStatusBuild,
		sysSwStatusActive
	}
	STATUS	 current
	DESCRIPTION
		"A collection of objects of sysSoftwareStatus MIB."
	::= { bigipSystemGroups 81 }

sysGlobalHostGroup OBJECT-GROUP
	 OBJECTS {
		sysGlobalHostResetStats,
		sysGlobalHostMemTotal,
		sysGlobalHostMemUsed,
		sysGlobalHostCpuCount,
		sysGlobalHostActiveCpuCount,
		sysGlobalHostCpuUser,
		sysGlobalHostCpuNice,
		sysGlobalHostCpuSystem,
		sysGlobalHostCpuIdle,
		sysGlobalHostCpuIrq,
		sysGlobalHostCpuSoftirq,
		sysGlobalHostCpuIowait,
		sysGlobalHostCpuUsageRatio,
		sysGlobalHostCpuUser5s,
		sysGlobalHostCpuNice5s,
		sysGlobalHostCpuSystem5s,
		sysGlobalHostCpuIdle5s,
		sysGlobalHostCpuIrq5s,
		sysGlobalHostCpuSoftirq5s,
		sysGlobalHostCpuIowait5s,
		sysGlobalHostCpuUsageRatio5s,
		sysGlobalHostCpuUser1m,
		sysGlobalHostCpuNice1m,
		sysGlobalHostCpuSystem1m,
		sysGlobalHostCpuIdle1m,
		sysGlobalHostCpuIrq1m,
		sysGlobalHostCpuSoftirq1m,
		sysGlobalHostCpuIowait1m,
		sysGlobalHostCpuUsageRatio1m,
		sysGlobalHostCpuUser5m,
		sysGlobalHostCpuNice5m,
		sysGlobalHostCpuSystem5m,
		sysGlobalHostCpuIdle5m,
		sysGlobalHostCpuIrq5m,
		sysGlobalHostCpuSoftirq5m,
		sysGlobalHostCpuIowait5m,
		sysGlobalHostCpuUsageRatio5m,
		sysGlobalHostCpuStolen,
		sysGlobalHostCpuStolen5s,
		sysGlobalHostCpuStolen1m,
		sysGlobalHostCpuStolen5m,
		sysGlobalHostMemTotalKb,
		sysGlobalHostMemUsedKb
	}
	STATUS	 current
	DESCRIPTION
		"A collection of objects of sysGlobalHost MIB."
	::= { bigipSystemGroups 82 }

sysModuleAllocationGroup OBJECT-GROUP
	 OBJECTS {
		sysModuleAllocationNumber,
		sysModuleAllocationName,
		sysModuleAllocationProvisionLevel,
		sysModuleAllocationMemoryRatio,
		sysModuleAllocationCpuRatio,
		sysModuleAllocationDiskRatio
	}
	STATUS	 current
	DESCRIPTION
		"A collection of objects of sysModuleAllocation MIB."
	::= { bigipSystemGroups 83 }

sysGlobalTmmStatGroup OBJECT-GROUP
	 OBJECTS {
		sysGlobalTmmStatResetStats,
		sysGlobalTmmStatNpus,
		sysGlobalTmmStatClientPktsIn,
		sysGlobalTmmStatClientBytesIn,
		sysGlobalTmmStatClientPktsOut,
		sysGlobalTmmStatClientBytesOut,
		sysGlobalTmmStatClientMaxConns,
		sysGlobalTmmStatClientTotConns,
		sysGlobalTmmStatClientCurConns,
		sysGlobalTmmStatServerPktsIn,
		sysGlobalTmmStatServerBytesIn,
		sysGlobalTmmStatServerPktsOut,
		sysGlobalTmmStatServerBytesOut,
		sysGlobalTmmStatServerMaxConns,
		sysGlobalTmmStatServerTotConns,
		sysGlobalTmmStatServerCurConns,
		sysGlobalTmmStatMaintenanceModeDeny,
		sysGlobalTmmStatMaxConnVirtualAddrDeny,
		sysGlobalTmmStatMaxConnVirtualPathDeny,
		sysGlobalTmmStatVirtualServerNonSynDeny,
		sysGlobalTmmStatNoHandlerDeny,
		sysGlobalTmmStatLicenseDeny,
		sysGlobalTmmStatCmpConnRedirected,
		sysGlobalTmmStatConnectionMemoryErrors,
		sysGlobalTmmStatTmTotalCycles,
		sysGlobalTmmStatTmIdleCycles,
		sysGlobalTmmStatTmSleepCycles,
		sysGlobalTmmStatMemoryTotal,
		sysGlobalTmmStatMemoryUsed,
		sysGlobalTmmStatDroppedPackets,
		sysGlobalTmmStatIncomingPacketErrors,
		sysGlobalTmmStatOutgoingPacketErrors,
		sysGlobalTmmStatHttpRequests,
		sysGlobalTmmStatTmUsageRatio5s,
		sysGlobalTmmStatTmUsageRatio1m,
		sysGlobalTmmStatTmUsageRatio5m,
		sysGlobalTmmStatMemoryTotalKb,
		sysGlobalTmmStatMemoryUsedKb
	}
	STATUS	 current
	DESCRIPTION
		"A collection of objects of sysGlobalTmmStat MIB."
	::= { bigipSystemGroups 84 }

sysPlatformInfoGroup OBJECT-GROUP
	 OBJECTS {
		sysPlatformInfoName,
		sysPlatformInfoMarketingName
	}
	STATUS	 current
	DESCRIPTION
		"A collection of objects of sysPlatformInfo MIB."
	::= { bigipSystemGroups 85 }

sysLogicalDiskGroup OBJECT-GROUP
	 OBJECTS {
		sysLogicalDiskNumber,
		sysLogicalDiskSlotId,
		sysLogicalDiskName,
		sysLogicalDiskDevname,
		sysLogicalDiskMedia,
		sysLogicalDiskSize,
		sysLogicalDiskFormat
	}
	STATUS	 current
	DESCRIPTION
		"A collection of objects of sysLogicalDisk MIB."
	::= { bigipSystemGroups 86 }

sysPhysicalDiskGroup OBJECT-GROUP
	 OBJECTS {
		sysPhysicalDiskNumber,
		sysPhysicalDiskSerialNumber,
		sysPhysicalDiskSlotId,
		sysPhysicalDiskName,
		sysPhysicalDiskIsArrayMember,
		sysPhysicalDiskArrayStatus
	}
	STATUS	 current
	DESCRIPTION
		"A collection of objects of sysPhysicalDisk MIB."
	::= { bigipSystemGroups 87 }

sysDiskBayGroup OBJECT-GROUP
	 OBJECTS {
		sysDiskBayNumber,
		sysDiskBayId,
		sysDiskBayDiskSerialNumber
	}
	STATUS	 current
	DESCRIPTION
		"A collection of objects of sysDiskBay MIB."
	::= { bigipSystemGroups 88 }

sysLogicalDiskMembersGroup OBJECT-GROUP
	 OBJECTS {
		sysLogicalDiskMembersNumber,
		sysLogicalDiskMembersDevname,
		sysLogicalDiskMembersSerialNumber,
		sysLogicalDiskMembersSlotId
	}
	STATUS	 current
	DESCRIPTION
		"A collection of objects of sysLogicalDiskMembers MIB."
	::= { bigipSystemGroups 89 }

sysProcPidStatGroup OBJECT-GROUP
	 OBJECTS {
		sysProcPidStatNumber,
		sysProcPidStatPid,
		sysProcPidStatProcName,
		sysProcPidStatCommandLine,
		sysProcPidStatModules,
		sysProcPidStatBladeNum,
		sysProcPidStatProcessor,
		sysProcPidStatUpdateTime,
		sysProcPidStatCpuUsageRecent,
		sysProcPidStatCpuUsage1min,
		sysProcPidStatCpuUsage5mins,
		sysProcPidStatSystemUsageRecent,
		sysProcPidStatSystemUsage1min,
		sysProcPidStatSystemUsage5mins,
		sysProcPidStatPpid,
		sysProcPidStatPgrp,
		sysProcPidStatState,
		sysProcPidStatSession,
		sysProcPidStatTtyNr,
		sysProcPidStatTpgid,
		sysProcPidStatFlags,
		sysProcPidStatMinFlt,
		sysProcPidStatCminFlt,
		sysProcPidStatMajFlt,
		sysProcPidStatCmajFlt,
		sysProcPidStatUtime,
		sysProcPidStatStime,
		sysProcPidStatCutime,
		sysProcPidStatCstime,
		sysProcPidStatPriority,
		sysProcPidStatNice,
		sysProcPidStatNumThreads,
		sysProcPidStatItrealvalue,
		sysProcPidStatStartTime,
		sysProcPidStatVsize,
		sysProcPidStatRss,
		sysProcPidStatRssRlim,
		sysProcPidStatStartCode,
		sysProcPidStatEndCode,
		sysProcPidStatStartStack,
		sysProcPidStatKstkEsp,
		sysProcPidStatKstkEip,
		sysProcPidStatSignal,
		sysProcPidStatBlocked,
		sysProcPidStatSigignore,
		sysProcPidStatSigcatch,
		sysProcPidStatWchan,
		sysProcPidStatNswap,
		sysProcPidStatCnswap,
		sysProcPidStatExitSignal,
		sysProcPidStatRtPriority,
		sysProcPidStatPolicy,
		sysProcPidStatProgSize,
		sysProcPidStatResident,
		sysProcPidStatShare,
		sysProcPidStatTSize,
		sysProcPidStatLSize,
		sysProcPidStatDSize,
		sysProcPidStatDirty
	}
	STATUS	 current
	DESCRIPTION
		"A collection of objects of sysProcPidStat MIB."
	::= { bigipSystemGroups 90 }

sysHttpCompressionStatGroup OBJECT-GROUP
	 OBJECTS {
		sysHttpCompressionStatResetStats,
		sysHttpCompressionStatPrecompressBytes,
		sysHttpCompressionStatPostcompressBytes,
		sysHttpCompressionStatNullCompressBytes,
		sysHttpCompressionStatHtmlPrecompressBytes,
		sysHttpCompressionStatHtmlPostcompressBytes,
		sysHttpCompressionStatCssPrecompressBytes,
		sysHttpCompressionStatCssPostcompressBytes,
		sysHttpCompressionStatJsPrecompressBytes,
		sysHttpCompressionStatJsPostcompressBytes,
		sysHttpCompressionStatXmlPrecompressBytes,
		sysHttpCompressionStatXmlPostcompressBytes,
		sysHttpCompressionStatSgmlPrecompressBytes,
		sysHttpCompressionStatSgmlPostcompressBytes,
		sysHttpCompressionStatPlainPrecompressBytes,
		sysHttpCompressionStatPlainPostcompressBytes,
		sysHttpCompressionStatOctetPrecompressBytes,
		sysHttpCompressionStatOctetPostcompressBytes,
		sysHttpCompressionStatImagePrecompressBytes,
		sysHttpCompressionStatImagePostcompressBytes,
		sysHttpCompressionStatVideoPrecompressBytes,
		sysHttpCompressionStatVideoPostcompressBytes,
		sysHttpCompressionStatAudioPrecompressBytes,
		sysHttpCompressionStatAudioPostcompressBytes,
		sysHttpCompressionStatOtherPrecompressBytes,
		sysHttpCompressionStatOtherPostcompressBytes
	}
	STATUS	 current
	DESCRIPTION
		"A collection of objects of sysGlobalHttpCompressionStat MIB."
	::= { bigipSystemGroups 91 }

sysWebAccelerationStatGroup OBJECT-GROUP
	 OBJECTS {
		sysWebAccelerationStatResetStats,
		sysWebAccelerationStatCacheHits,
		sysWebAccelerationStatCacheMisses,
		sysWebAccelerationStatCacheMissesAll,
		sysWebAccelerationStatCacheHitBytes,
		sysWebAccelerationStatCacheMissBytes,
		sysWebAccelerationStatCacheMissBytesAll,
		sysWebAccelerationStatCacheSize,
		sysWebAccelerationStatCacheCount,
		sysWebAccelerationStatCacheEvictions,
		sysWebAccelerationStatInterStripeHits,
		sysWebAccelerationStatInterStripeMisses,
		sysWebAccelerationStatInterStripeHitBytes,
		sysWebAccelerationStatInterStripeSize,
		sysWebAccelerationStatInterStripeCount,
		sysWebAccelerationStatInterStripeEvictions,
		sysWebAccelerationStatRemoteHits,
		sysWebAccelerationStatRemoteMisses,
		sysWebAccelerationStatRemoteHitBytes
	}
	STATUS	 current
	DESCRIPTION
		"A collection of objects of sysGlobalWebAccelerationStat MIB."
	::= { bigipSystemGroups 92 }

sysVlanStatGroup OBJECT-GROUP
	 OBJECTS {
		sysVlanStatNumber,
		sysVlanStatVlanName,
		sysVlanStatPktsIn,
		sysVlanStatBytesIn,
		sysVlanStatPktsOut,
		sysVlanStatBytesOut,
		sysVlanStatMcastIn,
		sysVlanStatMcastOut,
		sysVlanStatErrorsIn,
		sysVlanStatErrorsOut,
		sysVlanStatDropsIn,
		sysVlanStatDropsOut,
		sysVlanStatCollisions
	}
	STATUS	 current
	DESCRIPTION
		"A collection of objects of sysVlanStat MIB."
	::= { bigipSystemGroups 93 }

sysVlanxStatGroup OBJECT-GROUP
	 OBJECTS {
		sysVlanxStatNumber,
		sysVlanxStatVlanName,
		sysVlanxStatInMulticastPkts,
		sysVlanxStatInBroadcastPkts,
		sysVlanxStatOutMulticastPkts,
		sysVlanxStatOutBroadcastPkts,
		sysVlanxStatHcInOctets,
		sysVlanxStatHcInUcastPkts,
		sysVlanxStatHcInMulticastPkts,
		sysVlanxStatHcInBroadcastPkts,
		sysVlanxStatHcOutOctets,
		sysVlanxStatHcOutUcastPkts,
		sysVlanxStatHcOutMulticastPkts,
		sysVlanxStatHcOutBroadcastPkts,
		sysVlanxStatHighSpeed,
		sysVlanxStatConnectorPresent,
		sysVlanxStatCounterDiscontinuityTime
	}
	STATUS	 current
	DESCRIPTION
		"A collection of objects of sysVlanxStat MIB."
	::= { bigipSystemGroups 94 }

sysVcmpGroup OBJECT-GROUP
	 OBJECTS {
		sysVcmpNumber,
		sysVcmpVcmpName,
		sysVcmpHostname,
		sysVcmpSlots,
		sysVcmpState,
		sysVcmpMgmtNetwork,
		sysVcmpMgmtAddrType,
		sysVcmpMgmtAddr,
		sysVcmpMgmtNetmaskType,
		sysVcmpMgmtNetmask,
		sysVcmpMgmtGwType,
		sysVcmpMgmtGw,
		sysVcmpVcmpId,
		sysVcmpMgmtBaseMac,
		sysVcmpBaseMac,
		sysVcmpMacPoolSize,
		sysVcmpInitialImage,
		sysVcmpVirtualDisk,
		sysVcmpInitialHotfix,
		sysVcmpMinSlots,
		sysVcmpCoresPerSlot
	}
	STATUS	 current
	DESCRIPTION
		"A collection of objects of sysVcmp MIB."
	::= { bigipSystemGroups 95 }

sysVcmpCpuCoreGroup OBJECT-GROUP
	 OBJECTS {
		sysVcmpCpuCoreNumber,
		sysVcmpCpuCoreVcmpName,
		sysVcmpCpuCoreCpuCoreId
	}
	STATUS	 current
	DESCRIPTION
		"A collection of objects of sysVcmpCpuCore MIB."
	::= { bigipSystemGroups 96 }

sysVcmpVlanGroup OBJECT-GROUP
	 OBJECTS {
		sysVcmpVlanNumber,
		sysVcmpVlanVcmpName,
		sysVcmpVlanVlanName
	}
	STATUS	 current
	DESCRIPTION
		"A collection of objects of sysVcmpVlan MIB."
	::= { bigipSystemGroups 97 }

sysVcmpStatGroup OBJECT-GROUP
	 OBJECTS {
		sysVcmpStatNumber,
		sysVcmpStatVcmpName,
		sysVcmpStatVcmpId,
		sysVcmpStatSlotId,
		sysVcmpStatVmStatus,
		sysVcmpStatDiskUse,
		sysVcmpStatMemoryUse,
		sysVcmpStatBaseMac,
		sysVcmpStatMacPoolSize,
		sysVcmpStatCores,
		sysVcmpStatVdisk,
		sysVcmpStatStarts,
		sysVcmpStatRetries,
		sysVcmpStatUptime,
		sysVcmpStatComment,
		sysVcmpStatInterfaceNames,
		sysVcmpStatCoreNames,
		sysVcmpStatPrompt,
		sysVcmpStatCpuUsageRecent,
		sysVcmpStatCpuUsage1min,
		sysVcmpStatCpuUsage5mins,
		sysVcmpStatPktsIn,
		sysVcmpStatBytesIn,
		sysVcmpStatMcastIn,
		sysVcmpStatDropsIn,
		sysVcmpStatPktsOut,
		sysVcmpStatBytesOut,
		sysVcmpStatMcastOut,
		sysVcmpStatDropsOut
	}
	STATUS	 current
	DESCRIPTION
		"A collection of objects of sysVcmpStat MIB."
	::= { bigipSystemGroups 98 }

sysChassisSlotGroup OBJECT-GROUP
	 OBJECTS {
		sysChassisSlotNumber,
		sysChassisSlotSlotId,
		sysChassisSlotSerialNumber,
		sysChassisSlotDown,
		sysChassisSlotState
	}
	STATUS	 current
	DESCRIPTION
		"A collection of objects of sysChassisSlot MIB."
	::= { bigipSystemGroups 99 }

sysSysDeviceGroup OBJECT-GROUP
	 OBJECTS {
		sysSysDeviceNumber,
		sysSysDeviceName,
		sysSysDeviceMgmtIp,
		sysSysDeviceMgmtIpType,
		sysSysDeviceHostname,
		sysSysDeviceMirrorIp,
		sysSysDeviceMirrorIpType,
		sysSysDeviceMirrorSecondaryIp,
		sysSysDeviceMirrorSecondaryIpType,
		sysSysDeviceMulticastInterface,
		sysSysDeviceMulticastAddr,
		sysSysDeviceMulticastAddrType,
		sysSysDeviceMulticastPort,
		sysSysDeviceVersion,
		sysSysDeviceProduct,
		sysSysDeviceEdition,
		sysSysDeviceMarketingName,
		sysSysDevicePlatformId,
		sysSysDeviceChassisId
	}
	STATUS	 current
	DESCRIPTION
		"A collection of objects of sysSysDevice MIB."
	::= { bigipSystemGroups 100 }

sysUnicastAddrGroup OBJECT-GROUP
	 OBJECTS {
		sysUnicastAddrNumber,
		sysUnicastAddrName,
		sysUnicastAddrIndex,
		sysUnicastAddrSourceIp,
		sysUnicastAddrSourceIpType,
		sysUnicastAddrSourcePort
	}
	STATUS	 current
	DESCRIPTION
		"A collection of objects of sysUnicastAddr MIB."
	::= { bigipSystemGroups 101 }

sysSysDeviceActiveModulesGroup OBJECT-GROUP
	 OBJECTS {
		sysSysDeviceActiveModulesNumber,
		sysSysDeviceActiveModulesName,
		sysSysDeviceActiveModulesIndex,
		sysSysDeviceActiveModulesModule
	}
	STATUS	 current
	DESCRIPTION
		"A collection of objects of sysSysDeviceActiveModules MIB."
	::= { bigipSystemGroups 102 }

sysSysDeviceInactiveModulesGroup OBJECT-GROUP
	 OBJECTS {
		sysSysDeviceInactiveModulesNumber,
		sysSysDeviceInactiveModulesName,
		sysSysDeviceInactiveModulesIndex,
		sysSysDeviceInactiveModulesModule
	}
	STATUS	 current
	DESCRIPTION
		"A collection of objects of sysSysDeviceInactiveModules MIB."
	::= { bigipSystemGroups 103 }

sysSysDeviceOptionalModulesGroup OBJECT-GROUP
	 OBJECTS {
		sysSysDeviceOptionalModulesNumber,
		sysSysDeviceOptionalModulesName,
		sysSysDeviceOptionalModulesIndex,
		sysSysDeviceOptionalModulesModule
	}
	STATUS	 current
	DESCRIPTION
		"A collection of objects of sysSysDeviceOptionalModules MIB."
	::= { bigipSystemGroups 104 }

sysSysDeviceTimelimitedModulesGroup OBJECT-GROUP
	 OBJECTS {
		sysSysDeviceTimelimitedModulesNumber,
		sysSysDeviceTimelimitedModulesName,
		sysSysDeviceTimelimitedModulesIndex,
		sysSysDeviceTimelimitedModulesModule
	}
	STATUS	 current
	DESCRIPTION
		"A collection of objects of sysSysDeviceTimelimitedModules MIB."
	::= { bigipSystemGroups 105 }

sysStpGlobals2Group OBJECT-GROUP
	 OBJECTS {
		sysStpGlobals2Number,
		sysStpGlobals2Mode,
		sysStpGlobals2FwdDelay,
		sysStpGlobals2HelloTime,
		sysStpGlobals2MaxAge,
		sysStpGlobals2TransmitHold,
		sysStpGlobals2MaxHops,
		sysStpGlobals2Identifier,
		sysStpGlobals2Revision,
		sysStpGlobals2Name
	}
	STATUS	 current
	DESCRIPTION
		"A collection of objects of sysStpGlobals2 MIB."
	::= { bigipSystemGroups 106 }

sysCpuSensorGroup OBJECT-GROUP
	 OBJECTS {
		sysCpuSensorNumber,
		sysCpuSensorIndex,
		sysCpuSensorTemperature,
		sysCpuSensorFanSpeed,
		sysCpuSensorName,
		sysCpuSensorSlot
	}
	STATUS	 current
	DESCRIPTION
		"A collection of objects of sysCpuSensor MIB."
	::= { bigipSystemGroups 107 }

sysCmSyncStatusGroup OBJECT-GROUP
	 OBJECTS {
		sysCmSyncStatusId,
		sysCmSyncStatusStatus,
		sysCmSyncStatusColor,
		sysCmSyncStatusSummary
	}
	STATUS	 current
	DESCRIPTION
		"A collection of objects of sysCmSyncStatus MIB."
	::= { bigipSystemGroups 108 }

sysCmSyncStatusDetailsGroup OBJECT-GROUP
	 OBJECTS {
		sysCmSyncStatusDetailsNumber,
		sysCmSyncStatusDetailsIndex,
		sysCmSyncStatusDetailsDetails
	}
	STATUS	 current
	DESCRIPTION
		"A collection of objects of sysCmSyncStatusDetails MIB."
	::= { bigipSystemGroups 109 }

sysCmFailoverStatusGroup OBJECT-GROUP
	 OBJECTS {
		sysCmFailoverStatusId,
		sysCmFailoverStatusStatus,
		sysCmFailoverStatusColor,
		sysCmFailoverStatusSummary
	}
	STATUS	 current
	DESCRIPTION
		"A collection of objects of sysCmFailoverStatus MIB."
	::= { bigipSystemGroups 110 }

sysCmFailoverStatusDetailsGroup OBJECT-GROUP
	 OBJECTS {
		sysCmFailoverStatusDetailsNumber,
		sysCmFailoverStatusDetailsIndex,
		sysCmFailoverStatusDetailsDetails
	}
	STATUS	 current
	DESCRIPTION
		"A collection of objects of sysCmFailoverStatusDetails MIB."
	::= { bigipSystemGroups 111 }

sysCmTrafficGroupStatusGroup OBJECT-GROUP
	 OBJECTS {
		sysCmTrafficGroupStatusNumber,
		sysCmTrafficGroupStatusTrafficGroup,
		sysCmTrafficGroupStatusDeviceName,
		sysCmTrafficGroupStatusFailoverStatus
	}
	STATUS	 current
	DESCRIPTION
		"A collection of objects of sysCmTrafficGroupStatus MIB."
	::= { bigipSystemGroups 112 }

sysDnsStatGroup OBJECT-GROUP
	 OBJECTS {
		sysDnsStatResetStats,
		sysDnsStatQueries,
		sysDnsStatResponses,
		sysDnsStatResponsesPerSec,
		sysDnsStatToGtm,
		sysDnsStatDnsExpressReqs,
		sysDnsStatDnsExpressNotifies,
		sysDnsStatToCache,
		sysDnsStatToDns,
		sysDnsStatDns64Reqs,
		sysDnsStatDns64Rewrites,
		sysDnsStatDns64Failures,
		sysDnsStatHints,
		sysDnsStatRejects,
		sysDnsStatNoErrors,
		sysDnsStatDrops,
		sysDnsStatMalformed,
		sysDnsStatTclSuspends,
		sysDnsStatRecursionDesired,
		sysDnsStatCheckingDisabled,
		sysDnsStatEdns0,
		sysDnsStatOpcodeQuery,
		sysDnsStatOpcodeNotify,
		sysDnsStatOpcodeUpdate,
		sysDnsStatZoneIxfr,
		sysDnsStatZoneAxfr,
		sysDnsStatAuthoritativeAnswer,
		sysDnsStatRecursionAvailable,
		sysDnsStatAuthenticatedData,
		sysDnsStatTruncated,
		sysDnsStatRcodeNoerror,
		sysDnsStatRcodeNxdomain,
		sysDnsStatRcodeServfail,
		sysDnsStatRcodeRefused,
		sysDnsStatMalicious,
		sysDnsStatAReqs,
		sysDnsStatAaaaReqs,
		sysDnsStatAnyReqs,
		sysDnsStatCnameReqs,
		sysDnsStatMxReqs,
		sysDnsStatNsReqs,
		sysDnsStatPtrReqs,
		sysDnsStatSoaReqs,
		sysDnsStatSrvReqs,
		sysDnsStatTxtReqs,
		sysDnsStatOtherReqs
	}
	STATUS	 current
	DESCRIPTION
		"A collection of objects of sysGlobalDnsStat MIB."
	::= { bigipSystemGroups 113 }

sysLsnPoolStatGroup OBJECT-GROUP
	 OBJECTS {
		sysLsnPoolStatResetStats,
		sysLsnPoolStatActivePersistenceMappings,
		sysLsnPoolStatActiveInboundReservations,
		sysLsnPoolStatTranslationRequests,
		sysLsnPoolStatHairpinConnectionRequests,
		sysLsnPoolStatActiveTranslations,
		sysLsnPoolStatActiveHairpinConnections,
		sysLsnPoolStatTranslationRequestFailures,
		sysLsnPoolStatPersistenceMappingFailures,
		sysLsnPoolStatHairpinConnectionFailures,
		sysLsnPoolStatBackupPoolTranslations,
		sysLsnPoolStatLogAttempts,
		sysLsnPoolStatLogFailures
	}
	STATUS	 current
	DESCRIPTION
		"A collection of objects of sysGlobalLsnPoolStat MIB."
	::= { bigipSystemGroups 114 }

sysFecStatGroup OBJECT-GROUP
	 OBJECTS {
		sysFecStatResetStats,
		sysFecStatNumber,
		sysFecStatName,
		sysFecStatProfile,
		sysFecStatOutRawPackets,
		sysFecStatOutRawBytes,
		sysFecStatOutRdndPackets,
		sysFecStatOutRdndBytes,
		sysFecStatInRawPackets,
		sysFecStatInRawBytes,
		sysFecStatInRdndPackets,
		sysFecStatInRdndBytes,
		sysFecStatInRdndLost,
		sysFecStatInRawLost,
		sysFecStatRmtInRdndPackets,
		sysFecStatRmtInRdndLost,
		sysFecStatRmtInRawPackets,
		sysFecStatRmtInRawLost
	}
	STATUS	 current
	DESCRIPTION
		"A collection of objects of sysFecStat MIB."
	::= { bigipSystemGroups 115 }

sysVcmpAssignedSlotsGroup OBJECT-GROUP
	 OBJECTS {
		sysVcmpAssignedSlotsNumber,
		sysVcmpAssignedSlotsName,
		sysVcmpAssignedSlotsIndex,
		sysVcmpAssignedSlotsSlotId
	}
	STATUS	 current
	DESCRIPTION
		"A collection of objects of sysVcmpAssignedSlots MIB."
	::= { bigipSystemGroups 116 }

sysVcmpAllowedSlotsGroup OBJECT-GROUP
	 OBJECTS {
		sysVcmpAllowedSlotsNumber,
		sysVcmpAllowedSlotsName,
		sysVcmpAllowedSlotsIndex,
		sysVcmpAllowedSlotsSlotId
	}
	STATUS	 current
	DESCRIPTION
		"A collection of objects of sysVcmpAllowedSlots MIB."
	::= { bigipSystemGroups 117 }

sysVirtualDiskGroup OBJECT-GROUP
	 OBJECTS {
		sysVirtualDiskNumber,
		sysVirtualDiskFilename,
		sysVirtualDiskOperatingSystem,
		sysVirtualDiskSlotId,
		sysVirtualDiskState
	}
	STATUS	 current
	DESCRIPTION
		"A collection of objects of sysVirtualDisk MIB."
	::= { bigipSystemGroups 118 }
END
