-- =================================================================
-- Copyright (C) 2002 by  HUAWEI TECHNOLOGIES. All rights reserved.
--
-- Description:the huawei TC mib
-- Reference:
-- Version: V1.0
-- History:
--	
-- =================================================================
	HUAWEI-TC-MIB DEFINITIONS ::= BEGIN
 
		IMPORTS
			MODULE-IDENTITY			
				FROM SNMPv2-SMI			
			TEXTUAL-CONVENTION
				FROM SNMPv2-TC
			huawei
			    FROM HUAWEI-MIB;

	
		huaweiTCMIB MODULE-IDENTITY 
			LAST-UPDATED "0210010900Z"	
			ORGANIZATION 
				"
				HAUWEI MIB Standard community 
				"
			CONTACT-INFO 
				"tel:0755��6540808"
			DESCRIPTION 
			""

			REVISION "200206060900Z"		 
			DESCRIPTION
				"V1.1 20020606"

			REVISION "200204220900Z"		 
			DESCRIPTION
				"V1.1 200204220900 "
			::= { huawei 18 }
		


		HWErrorCode ::= TEXTUAL-CONVENTION
			STATUS deprecated
			DESCRIPTION 
				""
			SYNTAX INTEGER
				{
				noError(0),
				tooBig(1),
				noSuchName(2),
				badValue(3),
				readOnly(4),
				genErr(5),
				noAccess(6),
				wrongType(7),
				wrongLength(8),
				wrongEncoding(9),
				wrongValue(10),
				noCreation(11),
				inconsistentValue(12),
				resourceUnavailable(13),
				commitFailed(14),
				undoFailed(15),
				authorizationError(16),
				notWritable(17),
				inconsistentName(18),
				lastError(19),
				indexTypeWrong(400),
				indexExisted(401),
				indexNull(402),
				indexOverParas(403),
				indexLessParas(404),
				indexDefault(405),
				indexFull(406),
				stringNull(411),
				stringTooLong(412),
				stringTooShort(413),
				stringInvalidCharacters(414),
				stringNoEnd(415),
				stringMultiEnd(416),
				integerOnly(421),
				integerZero(422),
				integerTooLarge(423),
				integerTooSmall(424),
				ipAddrBrocast(431),
				ipAddrLoop(432),
				ipAddrOverLap(433),
				ipAddrOverflowed(434),
				ipAddrExisted(435),
				ipAddrNull(436),
				ipMaskNotMatch(438),
				ipAddrInvalid(439),
				ipMacWrongLength(440),
				ipMacWrongType(441),
				ipMaskAddrInvalid(442),
				memoryMallocError(470),
				memoryFreeError(471),
				memoryNullPoint(472),
				memoryProtected(473),
				memoryTooSmall(474),
				memoryTooBig(475)
				}

	HWFrameType ::= TEXTUAL-CONVENTION
			STATUS current
			DESCRIPTION 
				"This data type is used as the syntax of the
				hwframeType object in the definition of
				HUAWEI-DEVICE-MIBs hwframeTable."
			SYNTAX INTEGER
				{
				    fnameUnknow(1),
				    fnameMd16(2),			--MD 16 Slot Frame
				    fnameMd8(3),			--MD 8  Slot Frame
				    fnameMd4(4),			--MD 4  Slot Frame
				    fnameMa16(5),			--MA 16 Slot Frame
				    fnameMa8(6),			--MA 8  Slot Frame
				    fnameMa4(7),			--MA 4  Slot Frame
				    fnameSmx16(8),     		--MA 16 Slot Slave Frame
				    fnameRsa(9),          	--RSA Frame
				    fnameRsp19(10),			--RSP 19 Slot Frame
				    fnameRsp15(11),			--RSP 15 Slot Frame
				    fnameRsp14(12),			--RSP 14 Slot Frame
				    fnameRsp12(13),			--RSP 12 Slot Frame
				    fnameRsp10(14),			--RSP 10 Slot Frame
				    fnameRsp6A(15),			--RSP 6  Slot A Type Frame
				    fnameRsp6B(16),			--RSP 6  Slot B Type Frame
				    fnamePv819(17),			--PV8 19 Slot Frame
				    fnamePv815(18),			--PV8 15 Slot Frame
				    fnamePv814(19),			--PV8 14 Slot Frame
				    fnamePv812(20),			--PV8 12 Slot Frame
				    fnamePv810(21),			--PV8 10 Slot Frame
				    fnamePv86A(22),			--PV8 6 Slot A Type Frame
				    fnamePv86B(23),			--PV8 6 Slot B Type Frame
				    
				    
		             --Musa 
				    fnameMusa(50),	
				
				
			      --AG
				    fnamePvm10(60),
				    fnamePvm6B(61) ,

				-- A8010 
				    fnameA8010U18(70),	 -- A8010 18U
				    fnameA8010U5(71),    -- A8010
				    
				-- MA5105
				    fnameMA5105(80),     --MA5105
				    fnameBSL(81) ,        --BSL				    
				    fnameB08(82)         --B08
   				}


		HWPCBType ::= TEXTUAL-CONVENTION
			STATUS current
			DESCRIPTION 
				"This data type is used as the syntax of the 
				hwSlotType object in the definition of 
				HUAWEI-DEVICE-MIBs hwSlotTable.
				
				The definition of this textual convention with the
				addition of newly assigned values is published
				periodically by the Huawei MIB Criterion Group, every
				value indicate a PCB produced by Huawei.

"
			SYNTAX INTEGER
				{
          --MD 5500
                    bnameUnknown(1),
                    bnameH511Mmxa(2),			--MMXA board, mainboard of MA5100V1
                    bnameH511Mmxb(3),			--MMXB board, mainboard of MA5100V1 with APON sub-board
                    bnameH511Mmxc(4),			--MMXC board, mainboard of MA5100V2 with V5 characteritics etc.
                    bnameH511Asxa(5),			--ASXA board, mainboard of MD5500, with ASX chip on board for 8x622M switch
                    bnameH511Aica(6),			--ATM Interface Card, service board of MD5500, support STM-1 and STM-4
                    bnameH511Lanc(7),			--8 Port FE service board of MD/MA, for ethernet service access, support 64 VLAN
                    bnameH512Lanc(8),			--Update version of H511LANC, support 32/2K VLAN, and region VLAN (IPDSLAM)
                    bnameH512Land(9),			--Update version of H512LANC, support 32/256/2K VLAN (IPDSLAM), and 8FE/4FE/8Optic/4Optic/1GE subboard
                    bnameH511Adlb(10),			--
                    bnameH511Adlc(11),			--16 Port ADSL board
                    bnameH511Adld(12),			--32 Port ADSL board
                    bnameH512Adld(13),			--32 Port ADSL board, use another chipset contrast to H511ADLD
                    bnameH511Cesc(14),			--16 E1 Port CES board, not support TDM, with 2 E1 subboard
                    bnameH511Cesd(15),			--8 V35 Port CES board, with 3 V35 subboard
                    bnameH511Cese(16),			--8 E1 Port CES board, not support TDM, with 1 E1 subboard
                    bnameH511Cesf(17),			--No subboard, for TDM use
                    bnameH511Cesh(18),			--16 E1 port CES board, with 2 E1 subboard, support TDM
                    bnameH512Cesh(19),			--Same as H511CESH, diffrent from chipset
                    bnameH511Ea16(20),			--Same as H511CESC, diffrent from chipset
                    bnameH511Ce8(21),			--Same as H511CESE, diffrent from chipset
                    bnameH511Ce8V(22),			--Same as H511CESD, diffrent from chipset
                    bnameH511Dt16(23),			--16 E1 Port CES board, only support TDM mode
                    bnameH511Dn16(24),			--16 E1 Port CES board, only support TDM mode, support DDN clock
                    bnameH511Frca(25),			--8 E1 Port FR board
                    bnameH511Frcb(26),			--8 V35 Port FR board
                    bnameH511Slfa(27),			--8 G.SHDSL port FR board, work in E1 mode
                    bnameH511Slfb(28),			--8 G.SHDSL port FR board, work in V35 mode
                    bnameH511Slca(29),			--8 G.SHDSL port CES board, work in E1 mode, not support TDM
                    bnameH511Slcb(30),			--8 G.SHDSL port CES board, work in V35 mode
                    bnameH511Splb(31),			--16 port split board word with H511ADLC
                    bnameH511Splc(32),			--32 port split board word with H511ADLD/H512ADLD
                    bnameH511Pots(33),			--32 Port Pots board
                    bnameH511Aiua(34),			--ATM Interface Unit, can work with STM-1/IMA/E3 subboard, use the same PCB as MMXA
                    bnameH511Aiub(35),			--ATM Interface Unit, can work with STM-1/IMA/E3/APON/STM-4 subboard, use the same PCB as MMXA
		      		bnameH511Aiuc(36),			--ATM Interface Unit, can work with STM-1/IMA/E3/APON/STM-4 subboard, use the same PCB as MMXC
                    bnameH511Ipuo(37),			--Optic interface IP process board
                    bnameH511Epue(38),			--Electric Interface IP process board
                    bnameH511Ipue(39),			--Electric interface ehternet process board
                    bnameH511Epuo(40),			--Optic interface ehternet process board
                    bnameH511Vspd(41),			--VoDSL process board
                    bnameH511Msua(42),			--2 Port STM-1(with 2M structure) access board
                    bnameH511Imua(43),			--32 port IMA interface access board
                    bnameH511Smxa(44),			--main board in slave frame for DSLAM use, use the same PCB as MMXA
                    bnameH511Smxb(45),			--main board in slave frame for DSLAM use, use the same PCB as MMXB
                    bnameH511Sepa(46),			--Board used to connect slave frame for DSLAM use
                    bnameEsc(47),				--For HONET 
                    bnameRsp(48),				--For HONET
                    bnamePv8(49),				--For HONET
                    bnameApru(50),				--For HONET
                    bnameAprx(51),				--For HONET
                    bnameAsl(52),				--For HONET
                    bnameA32(53),				--For HONET
                    bnameDsl(54),				--For HONET
                    bnameMlc(55),				--For HONET
                    bnameIdla(56),				--For HONET
                    bnameCdi(57),				--For HONET
                    bnameAti(58),				--For HONET
                	bnameTss(59),				--For HONET
                	bnamePwx03(60),				--For HONET
                	bnamePwx04(61),				--For HONET
                	bnameEmu(62),				--For HONET
                    bnameHwc(63),				--For HONET
     
                  --MUSA ��Ʒ�������
			bnameSmb(80),		--main board
			bnameHrb(81),		
			bnameHab(82),		

                  --MA5200
			bnameNat(83),		 
			bnameCts(84),		 
				
		    --AG
			bnamePvm(90), 

		    -- A8010
 			bnamVspNas(110),    -- VSPNAS, AS31VSP103032106
 			bnamVspIpp(111),    -- VSP IPP,HSPAS31VSP103032106
 			bnamVspHsp(112),    -- VSP HSP AS31VSP103032106
 			bnamVspAnyport(113),-- VSP AnyPort AS31VSP103032106
			bnamVsu(114),    	-- AS31VSU103033127 ��AS31HSPA��
       		bnamHsp(115),    	--AS31MSTU03032762
 			bnamFrb(116),    	-- AS31FRB103034101��AS31FRBB03034102
			bnamMstu(117),    	-- AS31MSTU03032762

	            --ESR
	            bnameMpua(130) ,       --BS21MPUA
	            bnameMpub(131) ,               --BS22MPUB
	            bnameNeta(132) ,               --BS21NETA
	            bnameNetb(133) ,               --BS22NETB
	            bnameSFCA(134) ,               --BS21NETA
	            bnameLpua(135) ,               --BS21LPUA
	            bnameLpub(136) ,               --BS22LPUB
	            bnameLpuc(137) ,               --BS22LPUC
	            bnameLpud(138) ,               --BS22LPUD
	            
	            --ESR
	            bnameSpubBas(139) ,            --SN01SPUB
	            bnameSpubSerm(140) ,           --SN01SPUB
	            bnameLpui(141) ,               --SN01LPUI
	            bnameLpuh(142) ,               --SN01LPUH
	            bnameO2CC(143) ,               --BS2202CC
  
	            --MA5105
	                      bnameMa5105e1(200),             --E1
	                      bnameMa5105fe(201),             --FE
	                      bnameMa5105adsl(202),           --ADSL
	                      bnameMa5105ima(203),            --IMA
	          --MD5500
	                      bnameMD5500Hsl(204),    --HSL
	                      bnameMD5500PV4(205),     --PV4
	                      
	            
	            --HONET board type, for iManager N2000 BMS HV20 integrate management
	            bnameHV20ASL(300),               --For HONET, analog subscriber card of HONET SIPP II/III system, having 16 paths of subscriber lines on each card.
	            bnameHV20DRV(301),               --For HONET, dual-tone number receiving card of HONET SIPP II/III. Each card configures  16 dual-tone number receivers. Meanwhile, DRV card also provides the function of level switch between difference level and TTL level.
	            bnameHV20RSA(302),               --For HONET, a main board, usually used in remote subscriber shelf.
	            bnameHV20DTM(303),               --For HONET, digital trunk card of HONET SIPP II/III system. Each card provides 2 E1 interfaces.
	            bnameHV20DSL(304),               --For HONET, digital subscriber card of HONET SIPP II/III system. Each card configures 8 paths of digital subscriber lines.
	            bnameHV20DDU(305),               --For HONET, digital interface card of HONET SIPP II/III system. Each card performs the switch between 2 paths 64K bit/s signal and V35, V24 signals.
	            bnameHV20TSS(306),               --For HONET, test card of HONET SIPP II/III system, providing test for analog subscribers and digital subscribers.
	            bnameHV20TSI(307),               --For HONET, test card used in digital subscriber testing. This is no longer in use.
	            bnameHV20AV5(308),               --For HONET, maste r control card of HONET SIPP II/III system, responsible f or the protocol processing, equiment management, and network exchanging.
	            bnameHV20PWC(309),               --For HONET, power supply card of HONET SIPP II/III system. PWC card does not provide 48V generator, and is only used in the master control shelf of the SIPP II system.
	            bnameHV20PWX(310),               --For HONET, power supply card of HONET SIPP II/III system. PWX card provides 48V generator, which is used in various shelfs.
	            bnameHV20DM4(311),               --For HONET, tributary interface card. Each baord provides the 4 paths of switch between sub-synchronous PCM lines and 2112Kbit/s synchronous code, and 4 paths of inversion. It also determines the dirction of receiving and sending of the 4 paths of signals, which realizes the function of self-healing switch.
	            bnameHV20TIU(312),               --For HONET, optical interface card of OLT terminal station. The function of a TIU card is to multiplex the 28 paths of 2112 Kbit/s tributary signals sent by 7 DM4, and then send them back to the 7 DM4.
	            bnameHV20NMI(313),               --For HONET, used in OLT, ONU-512, ONU-128, ONU-1000A of the HONET system, functioning as maintenance of the optical transmission equipment, environment monitoring and equipment management.
	            bnameHV20FIU(314),               --For HONET, optical interface in the trunk ONU, providing simultaneously two pairs of optical interfaces.
	            bnameHV20EIU(315),               --For HONET, used in the E1 interface of ONU-128. EIU card completes the justification and restoration of two 2M signals.
	            bnameHV20BIU(316),               --For HONET, optical interface card used in triburary ONU, accepting 2 to 6 2M point to point transmission.
	            bnameHV20ILM(317),               --For HONET, InfoLink management card of CATV subscriber shelf.
	            bnameHV20ESC(318),               --For HONET, environment monitor interface card of HONET SIPP II/III system, providing the environment quantity of the remote ONU and monitoring the operation of the power supply.
	            bnameHV20PWH(319),               --For HONET, power supply card of PHD optical transmission system, used in various transmission shelfs.
	            bnameHV20ILR(320),               --For HONET, InfoLink optical receiving card of CATV subscriber shelf.
	            bnameHV20ILT(321),               --For HONET, InfoLink optical sending card of CATV subscriber shelf.
	            bnameHV20PV8(322),               --For HONET, the master control card of HONET SIPP II/III system, responsible for protocol handling, equipment management, and network switch. The only difference between PV8 card and PV4 card is that the former has 8 paths of standard E1 interfaces while the latter has only 4.
	            bnameHV20PV4(323),               --For HONET, the master control card of HONET SIPP II/III system, responsible for protocol handling, equipment management, and network switch. The only difference between PV8 card and PV4 card is that the former has 8 paths of standard E1 interfaces while the latter has only 4.
	            bnameHV20RSP(324),               --For HONET, a new-type remote RSA card of HONET SIPP II/III system whose convergence rate can be adjusted, connecting to remote ONU subscribers collaboratively with digital trunk cards. Each RSP card may configure at most 4 2M PCM links, and can realize 1:1, 1:2, and 1:4 convergence rates.
	            bnameHV20HSL(325),               --For HONET, N*64 super rate card (N=1~31), of HONET SIPP II/III system. Each card provides externally 2 synchronous V.35 interface in the mode of DCE or DTE, and two FE1 interfaces.
	            bnameHV20ATI(326),               --For HONET, analog trunk interface card of HONET SIPP II/III system, used to connect subscriber machines which have only EM interfaces, realizing EM communication transfer in the access network. Each AIT cards provides 6 physical EM ports. The slots are compatible with such card slots as ASL, DSL, and VFB.
	            bnameHV20SRX(327),               --For HONET, sub-rate card of HONET SIPP II/III system. Each card provides externally 5 synchronous/asynchronous compatible V.24 interfaces in DCE mode, completing the multiplexing of multiple sub-rate data specified in X.50 and X.58 protocols.
	            bnameHV20VFB(328),               --For HONET, 2 line/4 line voice frequency interface card of HONET SIPP II/III system, providing the private network of the railway dispatching system with private interface card.
	            bnameHV20VDM(329),               --For HONET, a card to stack sound frequencies in HONET SIPP II/III system. It is inserted in the subscriber shelf, and is compatible with other card slots in such cards as ASL, DSL, and VFB. Each VDM card has 16 channels, supporting at most 16 paths of voice frequency tiling.
	            bnameHV20CDI(330),               --For HONET, analog trunk card in HONET SIPP II/III system, supporting DDI service. CDI baord may dynamically distribute time slots, and its slots are compatible with the slots of such cards as ASL, DSL, and VFB.
	            bnameHV20ASP(331),               --For HONET, AV5 baord of the remote main node of HONET SIPP II/III system (HV201003 version or above not supportable),.
	            bnameHV20DTE(332),               --For HONET, a new- type 2M bit/s digital trunk interface card of HONET SIPP II/III system. Each card configures 8 2M PCM 30/32 systems.
	            bnameHV20WSA(333),               --For HONET, remote main node card which is wireless connected to ETS450 WLL base station in HONET SIPP II/III system. Each card outputs 2M E1 trunk, mainly used in WSA subscriber shelf. WSA card communicates with the host via RSA protocol, which equals to RSA main node card.
	            bnameHV20DTH(334),               --For HONET, 1.544M bit/s digital leased line interface card of HONET SIPP II/III system. Each card configures 8 1.544M PCM 22/24 systems, providing T1 leased line service.
	            bnameHV20ASL32(335),             --For HONET, a new-type analog subscriber card of HONET SIPP II/III system, which can provide 32 paths of subscriber lines on each card.
	            bnameHV20NPU(336),               --For HONET, net process unit in HONET SIPP II/III system, which can provide 10M ethernet interface .
	            bnameHV20DLI(337),               --For HONET, DECT interface board, which provide 32 channle for wireless subscriber.
	            bnameHV20CKS(338),               --For HONET, a clock card of HONET SIPP II/III system.
	            bnameHV20CKD(339),               --For HONET, a clock card of HONET SIPP II/III system.
	            bnameHV20SBL(340),               --For HONET, 2B1Q card of HONET SIPP II/III system. Each card provides 8 paths of 2B1Q interfaces, which are used in DDN access.
	            bnameHV20MLC(341),               --For HONET, a new-type SBL card, can be used as both subscriber card and main node board.
	            bnameHV20SCS(342),               --For HONET, SCS Card is subrate concentrate switch card that is used with SRX Card, MTA port, DE1 Channel, and this card only support connection between subrate of 2.4K, 4.8K, 9.6K, 19.2K.
	            bnameHV20HWC(343)                --For HONET, a signal level convert board, only used for PV8 board in PV8-10 control shelf.
				}
	
					

		HWSubPCBType ::= TEXTUAL-CONVENTION
			STATUS current
			DESCRIPTION 
				"This data type is used as the syntax of the
				hwSubslotType object in the definition of
				HUAWEI-DEVICE-MIB's hwSubslotTable."
			SYNTAX INTEGER
				{
				    subbnameunknown(1),
    			    subbnameh511o2ctg(2),	--SM 30Km-2 path 155M ATM��MA
				    subbnameh511o2ctb(3),	--MM 2Km-2 path 155M ATM��MA 
				    subbnameh511o1ctg(4),	
				    subbnameh511o1ctb(5),	
				    subbnameh511v2ht(6),	 
				    subbnameh511v1ht(7),	 
				    subbnameh512o8ffb(8), 	 
				    subbnameh512o8fff(9), 	 
				    subbnameh511o1gfa(10), 	
				    subbnameh511o1gfe(11), 	--reserve
				    subbnameh511o1gfg(12), 	--reserve
				    subbnameh511o2cpb(13), 	
				    subbnameh511o2cpg(14), 	
				    subbnameh511o1cpb(15),	
				    subbnameh511o1cpg(16),  
				    subbnameh511o1hxc(17),
				    subbnameh511o1hxb(18),
				    subbnameh511o1hxa(19),
				    subbnameh511e23t(20),
				    subbnameh511e13t(21),
				    subbnameh511t23t(22),	
				    subbnameh511t13t(23),
				    subbnameh511o2cvb(24),
				    subbnameh511o2cvg(25),
				    subbnameh511e8it(26), 
				    subbnameh511e81d(27),
				    subbnameh511e8vd(28),
				    subbnameh511s81d(29),
				    subbnamevc01sdsp(30),
				   
 -- 20020619 ����
				    subbnameh511o1gfx(31),
				    subbnameh511e8fi(32),
				    subbnameh511o1cvb(33),
				    subbnameh511o1cvg(34),
				    
				    
				    --MA5200
				    subbnameaim1(50),
				    subbnameaim2(51),
				    subbnameaim3(52),
				    subbnameaim4(53),
 				    subbnamepim1(54),
				    subbnamepim2(55),
				    subbnamepim3(56),
				    subbnamepim4(57),
            --ESR �ӿ�����
					subbnameAtm155(130) ,  	
					subbnameAtm622(131) ,  	
					subbnamePos155 (132) ,  
					subbnamePos622(133) ,  	--BS22P2HA
					subbnameO2cc   (134) ,  
					subbnameE43a(135) ,  	
					subbnameE8fi (136) ,  	--SN01E8FI
					subbnameO8fi (137) ,  	--SN01O8FI
					subbnameO1gi (138) ,  	--SN01O1GI
					subbnameE8f(139),   	
					subbnameO8f (140) ,  	
					subbnameO1g (141) ,  
					subbnameO2g (142) ,  
					subbnameO8g (143) ,  
					subbnameAtm2g5(144) ,
					subbnameBfm(145),   
		-- A8010 ��Ʒ
                    subbnameCkmb(65536),   	
                    subbnameP2ci(65537),        
                    subbnameCsma(65538),        
                    subbnameCsmb(65539),        
                    subbnameCsmc(65540),        
                    subbnameCsmd(65541),        
                    subbnameCkma(65542),        
		    subbnameCkmc(65543),        
		    subbnameO8fib(65544),       
		    subbnameO8fif(65545),       
		    subbnameO1gie(65546),       
		    subbnameO1gig(65547),       
		    subbnameO1gii(65548),       
		    subbnameO1gia(65549),       
		    subbnameOgfib(65550),       
		    subbnameOgfif(65551),       
		    subbnameO2gie(65552),       
		    subbnameO2gia(65553),       
		    subbnameP2cig(65554),       
		    subbnameP2cib(65555),       
		    subbname8efi(65556),        
		    subbnameO2cib(65557),       
		    subbnameO2cig(65558),       
		    subbnameE2ai(65559),        
		    subbnameE8vd (65560),       
		    subbnameE81d (65561),       
		    subbnameLdcu (65562),       
		    subbnameLiua (65563),       
		    subbnameLiub (65564),       
		    subbnameLiuc (65565) ,      
--MA5100 ��Ʒ		      			
		    subbnameApc(65836)   	
				}
			


	
          HWPortType ::= TEXTUAL-CONVENTION
             STATUS       current
             DESCRIPTION
               "This data type is used as the syntax of the ifType
               object in the (updated) definition of MIB-II's
               ifTable.

               The definition of this textual convention with the
               addition of newly assigned values is published
               periodically by the IANA, in either the Assigned
               Numbers RFC, or some derivative of it specific to
               Internet Network Management number assignments.  (The
               latest arrangements can be obtained by contacting the
               IANA.)

               Requests for new values should be made to IANA via
               email (iana@iana.org).

               The relationship between the assignment of ifType
               values and of OIDs to particular media-specific MIBs
               is solely the purview of IANA and is subject to change
               without notice.  Quite often, a media-specific MIB's
               OID-subtree assignment within MIB-II's 'transmission'
               subtree will be the same as its ifType value.
               However, in some circumstances this will not be the
               case, and implementors must not pre-assume any
               specific relationship between ifType values and
               transmission subtree OIDs."
       SYNTAX  INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),            -- DS1-MIB
                   e1(19),             -- Obsolete see DS1-MIB
                   basicISDN(20),
                   primaryISDN(21),
                   propPointToPointSerial(22), -- proprietary serial
                   ppp(23),
                   softwareLoopback(24),
                   eon(25),            -- CLNP over IP 
                   ethernet3Mbit(26),
                   nsip(27),           -- XNS over IP
                   slip(28),           -- generic SLIP
                   ultra(29),          -- ULTRA technologies
                   ds3(30),            -- DS3-MIB
                   sip(31),            -- SMDS, coffee
                   frameRelay(32),     -- DTE only. 
                   rs232(33),
                   para(34),           -- parallel-port
                   arcnet(35),         -- arcnet
                   arcnetPlus(36),     -- arcnet plus
                   atm(37),            -- ATM cells
                   miox25(38),
                   sonet(39),          -- SONET or SDH 
                   x25ple(40),
                   iso88022llc(41),
                   localTalk(42),
                   smdsDxi(43),
                   frameRelayService(44), -- FRNETSERV-MIB
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54),-- proprietary multiplexing
                   ieee80212(55),      -- 100BaseVG
                   fibreChannel(56),   -- Fibre Channel
                   hippiInterface(57), -- HIPPI interfaces     
                   frameRelayInterconnect(58), -- Obsolete use either  frameRelay(32) or frameRelayService(44).
                   aflane8023(59),     -- ATM Emulated LAN for 802.3
                   aflane8025(60),     -- ATM Emulated LAN for 802.5
                   cctEmul(61),        -- ATM Emulated circuit          
                   fastEther(62),      -- Fast Ethernet (100BaseT)
                   isdn(63),           -- ISDN and X.25           
                   v11(64),            -- CCITT V.11/X.21             
                   v36(65),            -- CCITT V.36                  
                   g703at64k(66),      -- CCITT G703 at 64Kbps
                   g703at2mb(67),      -- Obsolete see DS1-MIB
                   qllc(68),           -- SNA QLLC                    
                   fastEtherFX(69),    -- Fast Ethernet (100BaseFX)   
                   channel(70),        -- channel                     
                   ieee80211(71),      -- radio spread spectrum       
	           ibm370parChan(72),      -- IBM System 360/370 OEMI Channel
                   escon(73),          -- IBM Enterprise Systems Connection
                   dlsw(74),           -- Data Link Switching
                   isdns(75),          -- ISDN S/T interface
                   isdnu(76),          -- ISDN U interface
                   lapd(77),           -- Link Access Protocol D
                   ipSwitch(78),       -- IP Switching Objects
                   rsrb(79),           -- Remote Source Route Bridging
                   atmLogical(80),     -- ATM Logical Port
                   ds0(81),            -- Digital Signal Level 0
                   ds0Bundle(82),      -- group of ds0s on the same ds1
                   bsc(83),            -- Bisynchronous Protocol
                   async(84),          -- Asynchronous Protocol
                   cnr(85),            -- Combat Net Radio
                   iso88025Dtr(86),    -- ISO 802.5r DTR
                   eplrs(87),          -- Ext Pos Loc Report Sys
                   arap(88),           -- Appletalk Remote Access Protocol
                   propCnls(89),       -- Proprietary Connectionless Protocol
                   hostPad(90),        -- CCITT-ITU X.29 PAD Protocol
                   termPad(91),        -- CCITT-ITU X.3 PAD Facility
                   frameRelayMPI(92),  -- Multiproto Interconnect over FR
                   x213(93),           -- CCITT-ITU X213
                   adsl(94),           -- Asymmetric Digital Subscriber Loop
                   radsl(95),          -- Rate-Adapt. Digital Subscriber Loop
                   sdsl(96),           -- Symmetric Digital Subscriber Loop
                   vdsl(97),           -- Very H-Speed Digital Subscrib. Loop
                   iso88025CRFPInt(98),  -- ISO 802.5 CRFP
                   myrinet(99),        -- Myricom Myrinet
                   voiceEM(100),       -- voice recEive and transMit
                   voiceFXO(101),      -- voice Foreign Exchange Office
                   voiceFXS(102),      -- voice Foreign Exchange Station
                   voiceEncap(103),    -- voice encapsulation
                   voiceOverIp(104),   -- voice over IP encapsulation
                   atmDxi(105),        -- ATM DXI
                   atmFuni(106),       -- ATM FUNI
		           atmIma (107),       -- ATM IMA		   
                   pppMultilinkBundle(108), -- PPP Multilink Bundle
                   ipOverCdlc (109),   -- IBM ipOverCdlc
		           ipOverClaw (110),   -- IBM Common Link Access to Workstn
                   stackToStack (111), -- IBM stackToStack
                   virtualIpAddress (112), -- IBM VIPA
				   mpc (113),          -- IBM multi-protocol channel support
				   ipOverAtm (114),    -- IBM ipOverAtm
				   iso88025Fiber (115), -- ISO 802.5j Fiber Token Ring
				   tdlc (116),	       -- IBM twinaxial data link control
				   gigabitEthernet (117), -- Gigabit Ethernet
				   hdlc (118),         -- HDLC
				   lapf (119),	       -- LAP F
				   v37 (120),	       -- V.37
				   x25mlp (121),       -- Multi-Link Protocol
				   x25huntGroup (122), -- X25 Hunt Group
				   trasnpHdlc (123),   -- Transp HDLC
				   interleave (124),   -- Interleave channel
				   fast (125),         -- Fast channel
				   ip (126),	       -- IP (for APPN HPR in IP networks)
				   docsCableMaclayer (127),  -- CATV Mac Layer
				   docsCableDownstream (128), -- CATV Downstream interface
				   docsCableUpstream (129),  -- CATV Upstream interface
				   a12MppSwitch (130), -- Avalon Parallel Processor
				   tunnel (131),       -- Encapsulation interface
				   coffee (132),       -- coffee pot
				   ces (133),          -- Circuit Emulation Service
				   atmSubInterface (134), -- ATM Sub Interface
				   l2vlan (135),       -- Layer 2 Virtual LAN using 802.1Q
				   l3ipvlan (136),     -- Layer 3 Virtual LAN using IP
				   l3ipxvlan (137),    -- Layer 3 Virtual LAN using IPX
				   digitalPowerline (138), -- IP over Power Lines	
				   mediaMailOverIp (139), -- Multimedia Mail over IP
				   dtm (140),              -- Dynamic syncronous Transfer Mode
				   dcn (141),              -- Data Communications Network
				   ipForward (142),        -- IP Forwarding Interface
				   msdsl (143),            -- Multi-rate Symmetric DSL
				   ieee1394 (144), 			-- IEEE1394 High Performance Serial Bus
				   if-gsn (145),       		--   HIPPI-6400 
				   dvbRccMacLayer (146), 	-- DVB-RCC MAC Layer
				   dvbRccDownstream (147),  -- DVB-RCC Downstream Channel
				   dvbRccUpstream (148),  -- DVB-RCC Upstream Channel
				   atmVirtual (149),   		-- ATM Virtual Interface
				   mplsTunnel (150),   -- MPLS Tunnel Virtual Interface
				   srp (151),	-- Spatial Reuse Protocol	
				   voiceOverAtm (152),  -- Voice Over ATM
				   voiceOverFrameRelay (153),   -- Voice Over Frame Relay 
				   idsl (154),		-- Digital Subscriber Loop over ISDN
				   compositeLink (155),  -- Avici Composite Link Interface
				   ss7SigLink (156),     -- SS7 Signaling Link 
				   propWirelessP2P (157),  --  Prop. P2P wireless interface
				   frForward (158),    -- Frame Forward Interface
				   rfc1483 (159),	-- Multiprotocol over ATM AAL5
				   usb (160),		-- USB Interface
				   ieee8023adLag (161),  -- IEEE 802.3ad Link Aggregate
                   bgppolicyaccounting (162), -- BGP Policy Accounting
                   frf16MfrBundle (163), -- FRF .16 Multilink Frame Relay 
                   h323Gatekeeper (164), -- H323 Gatekeeper
                   h323Proxy (165), -- H323 Voice and Video Proxy
                   mpls (166), -- MPLS                   
                   mfSigLink (167), -- Multi-frequency signaling link
                   hdsl2 (168), -- High Bit-Rate DSL - 2nd generation
                   shdsl (169), -- Multirate HDSL2
                   ds1FDL (170), -- Facility Data Link 4Kbps on a DS1
                   pos (171), -- Packet over SONET/SDH Interface
                   dvbAsiIn (172), -- DVB-ASI Input
                   dvbAsiOut (173), -- DVB-ASI Output 
                   plc (174), -- Power Line Communtications
                   nfas (175), -- Non Facility Associated Signaling
                   tr008 (176), -- TR008
                   gr303RDT (177), -- Remote Digital net.itransformers.topologyviewer.rightclick.impl.Terminal
                   gr303IDT (178), -- Integrated Digital net.itransformers.topologyviewer.rightclick.impl.Terminal
                   isup (179), -- ISUP
                   propDocsWirelessMaclayer (180), -- prop/Maclayer
                   propDocsWirelessDownstream (181), -- prop/Downstream
                   propDocsWirelessUpstream (182), -- prop/Upstream
                   hiperlan2 (183), -- HIPERLAN Type 2 Radio Interface
                   propBWAp2Mp (184), -- PropBroadbandWirelessAccesspt2multipt
                   sonetOverheadChannel (185), -- SONET Overhead Channel
                   digitalWrapperOverheadChannel (186), -- Digital Wrapper
                   aal2 (187), -- ATM adaptation layer 2
                   radioMAC (188), -- MAC layer over radio links
                   atmRadio (189), -- ATM over radio links   
                   imt (190), -- Inter Machine Trunks
                   mvl (191), -- Multiple Virtual Lines DSL
                   reachDSL (192), -- Long Rach DSL
                   frDlciEndPt (193), -- Frame Relay DLCI End Point
                   atmVciEndPt (194), -- ATM VCI End Point
                   opticalChannel (195), -- Optical Channel
                   opticalTransport (196), -- Optical Transport
                   propAtm (197), --  Proprietary ATM       
                   voiceOverCable (198), -- Voice Over Cable Interface
                   infiniband (199), -- Infiniband
                   teLink (200), -- TE Link
                   q2931 (201), -- Q.2931
                   virtualTg (202), -- Virtual Trunk Group
                   sipTg (203), -- SIP Trunk Group
                   sipSig (204), -- SIP Signaling   
                   docsCableUpstreamChannel (205), -- CATV Upstream Channel
                   econet (206), -- Acorn Econet
                   pon155 (207), -- FSAN 155Mb Symetrical PON interface
                   pon622 (208), -- FSAN622Mb Symetrical PON interface
                   bridge (209), -- Transparent bridge interface
                   linegroup (210), -- Interface common to multiple lines		   
                   voiceEMFGD (211), -- voice E&M Feature Group D
                   voiceFGDEANA (212), -- voice FGD Exchange Access North American
                   voiceDID (213), -- voice Direct Inward Dialing

                
                    aponOltPort(501),			--Apon olt port
                    aponOltSubport(502),		--Apon olt sub port
                    aponOntPort(503),			--Apon ont port
                    atmPort(504), 				--atm port
                    atmSubport(505),			--atm sub port
                    adslPort(506),		        -- RFC��׼���Ѿ��ж��壬�����ٶ��� 
                    lancPort(507),				--lan port
                    cescPort(508),				--E1 port of CESC board
                    cesdPort(509),				--V35 port of CESD board
                    frcPort(510),				--E1 port FR board
                    fpcSubport(511),			--
                    sepPort(512),				--
                    vpringPort(513),			--STM-4 VPRING port
                    eimPort(514),				--FE port of BAS board
                    geimPort(515),				--GE port of BAS board
                    basMainport(516),			--ATM port of BAS board used to create connection
                    apruCes(517),				--Apon CES port
                    apruLan(518),				--Apon LAN port
                    asxSoftSar(519),			--soft sar port of ASX board
                    asxHardSar(520),			--hard sar port of ASX board
                    cesE1Port(521),				--E1 port of CES board, for TDM use
                    e1Port(522),				--E1 port of CES
                    t1Port(523),				--T1 port of CES
                    pstnPort(524),				
                    braPort(525),
                    praPort(536),
                    cdiPort(539),
                    vfbPort(540),
                    atiPort(541),
                    mlcE1Port(542),
                    v5TkPort(543),
                    comPort(544),
                    v35Port(545),				--
                    mmxIwe8Port(546),			--CES port on MMXC board
                    frPortE1(547),				--E1 port of FR board
                    frPortT1(548),				--T1 port of FR board
                    frPortV35(549),				--V35 port of FR board
                    aiuAtmPort(550),			--ATM port on AIU board
                    aiuImaPort(551),			--IMA port on AIU board
                    aiuE3Port(552),				--E3 port on AIU board
                    mmxE3Port(553),				--E3 port on MMX board
                    mmxImaPort(554),			--IMA port on MMX board
                    nullPort(555),				
                    shdslPort(556),				--G.SHDSL  port
                    iadMainport(557),
                    iadPort(558),				--
				    cesSDTVPort(559),         	--CES SDT virtual port
				    vlanVPort(560),           	--VLAN virtual port of LAN board
				    frVCCIndexVPort(561),     	--FR VCC virtual port
				    frStreamVPort(562),       	--FR stream virtual port
				    imaGroupVPort(563),       	--IMA group virtual port
				    adslInterleaveVPort(564), 	--Interleavet virtual port of ADSL board
				    adslFastVPort(565),			--Fast virtual port of ADSL board
				    lanTrunkVPort(566),			--Trunk virtual port of LAN board
                    
		--MA5200
		    debugserial(580),
		    debugnet(581),

		--8010    
		   dsp(65536),             
		   bits(65537),
		   clk(65538),
		   mon(65539),
		   aux(65540),
		   sdho(65541),
		   sdhe(65542)
				}

    
	
	END
