-- *****************************************************************
-- CISCO-STACK-MIB.my
--
-- June 1995, Fei Xu
--
-- Copyright (c) 1995-2007 by cisco Systems, Inc.
-- All rights reserved.
-- *****************************************************************
--
CISCO-STACK-MIB DEFINITIONS ::= BEGIN

IMPORTS
        MODULE-IDENTITY, OBJECT-TYPE, IpAddress, TimeTicks,
        Counter32, Counter64, Unsigned32, NOTIFICATION-TYPE
                FROM SNMPv2-SMI
        DisplayString, RowStatus, TruthValue, MacAddress,
        TEXTUAL-CONVENTION
                FROM SNMPv2-TC
        fddimibPORTSMTIndex, fddimibPORTIndex
                FROM FDDI-SMT73-MIB
        OwnerString, ifName, ifIndex
                FROM IF-MIB
        MODULE-COMPLIANCE, OBJECT-GROUP, NOTIFICATION-GROUP
                FROM SNMPv2-CONF
        workgroup
                FROM CISCO-SMI
        ringStationMacAddress
                FROM TOKEN-RING-RMON-MIB
        PhysicalIndex
                FROM ENTITY-MIB
        VlanIndex
                FROM CISCO-VTP-MIB;

ciscoStackMIB MODULE-IDENTITY
        LAST-UPDATED        "200712120000Z"
        ORGANIZATION        "Cisco Systems, Inc."
        CONTACT-INFO
                "       Cisco Systems
                        Customer Service

                Postal: 170 W Tasman Drive
                        San Jose, CA  95134
                        USA

                   Tel: +1 800 553-NETS

                E-mail: cs-wbu@cisco.com,
                        cs-lan-switch-snmp@cisco.com"

        DESCRIPTION
                "This MIB provides configuration and runtime status for
                 chassis, modules, ports, etc. on the Catalyst systems."

        REVISION "200712120000Z"
        DESCRIPTION
                 "Modified chassisSysType for new hardwares:
                 'wsc6509ve'.

                 Modified chassisComponentType for new hardwares:
                 'wsc6509veFan'.

                 Modified chassisPs1Type and chassisPs2Type to include:
                 'pwr6000dc', 'pwr4500dc'.

                 Modified moduleType to include:
                 'wssup32pge', 'wssup32p10ge', 'wssvcpisa32', 'wsf6kmsfc2a',
                 'wsSvcMwam1', 'wsSvcPsd1', 'wsSvcSamiBb', 'vss72010g',
                 'wsx671610ge'.

                 Modified moduleSubType to include new hardwares:
                 'vsf6kpfc3cxl', 'vsf6kpfc3c'.

                 Modified moduleSubType2 to include new hardwares:
                 'vsf6kmsfc3', 'me6524msfc2a', 'wssvcpisa32'.

                 Modified portType to include:
                 'intrusionProtect', 'e1000BaseSvc', 'e10GBaseSvc',
                 'e10GBaseLRM', 'e10GBaseT'.

                 Modified syslogMessageFacility to include:
                 'dom', 'mvrp'.

                 Added ipPermitGroup3."

        REVISION "200705290000Z"
        DESCRIPTION
                 "Modified moduleType to include 'wsx6066SlbSk9'."

        REVISION "200705250000Z"
        DESCRIPTION
                 "Updated chassisPs1Type and chassisPs2Type to include:
                 'pwr1500dc'.

                 Modified moduleType to include:
                 'osm12t3e3', 'osm4GeWanGbicPlus', 'm7600Sip600',
                 'm7600Sip200', 'm7600Sip400', 'c7600ssc400',
                 'c7600ssc600', 'esm2x10ge', 'rsp720', 'rsp720base', 
                 'c7600msfc4'.

                 Updated moduleSubType to include new hardwares:
                 'm7600pfc3c', 'sip600earl', 'c7600esmdfc3cxl',
                 'c7600esmdfc3c'.

                 Updated moduleSubType2 to include new hardwares:
                 'esm2x10ge', 'c7600msfc4'."

        REVISION "200703300000Z"
        DESCRIPTION
                 "Modified chassisSysType to include:
                 'mec6524gs8s', 'mec6524gt8s', 'cisco7603s'.

                 Updated chassisPs1Type and chassisPs2Type to include:
                 'pwr400dc', 'pwr400ac'.

                 Updated chassisComponentType for new hardwares:
                 'fan6524', 'fanMod6Shs', 'fanMod9Shs', 'fanMod9St',
                 'fanMod3Hs'.

                 Modified moduleType to include:
                 'mec6524gs8s', 'mec6524gt8s', 'me6524msfc2a',
                 'wsx670810ge'.

                 Updated moduleSubType to include new hardwares:
                 'mec6524pfc3c', 'wsf6700dfc3c', 'wsf6700dfc3cxl'.

                 Modified VendorIdType to compliance with SNMP v2
                 format"

        REVISION "200510280000Z"
        DESCRIPTION
                 "Modified chassisComponentType to include:
                 'fanMod4Hs'.

                 Modified syslogMessageFacility to include:
                 'eou', 'backup', 'eoam', 'webauth'.

                 Modified sysErrDisableTimeoutEnable to include:
                 'ethernetOam', 'gl2ptEoamThresholdExceed'.

                 Updated chassisPs1Type and chassisPs2Type to include:
                 'pwr2700dc', 'pwr2700ac4', 'pwr2700dc4', and
                 'wscac8700we'.

                 Modified moduleType to include:
                 'osm4oc3PosMM', 'wsx6196rj21', 
                 'wssup32ge3b', 'wsSvcIpSec1',
                 'wsx6148arj45', 'wsSvcWebVpnk9',
                 'ace106500k9', 'ace046500k9',
                 'wsSvcAdm1k9', 'wsSvcAgm1k9',
                 'wssup3210ge3b', 'osm2choc12T3SI',
                 'wsf6700cfc', 'osm8choc3DS0SI'.

                 Updated portType to include:
                 'e10GBaseEdc1310', 'e10GBaseSW',
                 'sslVpn', 'adsm',
                 'agsm', 'aces',
                 'e10GBaseZR', 'e100BaseEX',
                 'e100BaseZX'."

        REVISION "200504270000Z"
        DESCRIPTION
                "Added support of the following objects:
                 cisco7604sysID, wsc6504esysID

                 Modified sysEnableStpxTrap to include:
                 'enabledForInconOnly', 'enabledForRootOnly',
                 'enabledForLoopOnly', 'enabledForInconRootOnly',
                 'enabledForInconLoopOnly', 'enabledForRootLoopOnly'

                 Modified sysErrDisableTimeoutEnable to include:
                 'camMonitor', 'gl2ptCdpThresholdExceed',
                 'gl2ptStpThresholdExceed', 'gl2ptVtpThresholdExceed',
                 'linkRxCrc', 'linkTxCrc',
                 'linkInErrors', 'packetBufferError'

                 Updated chassisSysType for new hardwares:
                 cisco7604 and wsc6504e

                 Updated chassisPs1Type and chassisPs2Type for new
                 hardwares:
                 wscac6000w and pwr2700ac

                 Updated chassisComponentType for new hardwares:
                 wsc6506eFan, wsc6509eFan, wsc6503eFan, wsc6000vtte.

                 Updated moduleType for hardware:
                 osm2oc48OneDptSSDual, osm2oc48OneDptSIDual,
                 osm2oc48OneDptSLDual, osm4choc12T3MM,
                 osm4choc12T3SI, osm8choc12T3MM,
                 osm8choc12T3SI, osm2choc48T3SS,
                 osm1choc48T3SI, osm2choc48T3SI,
                 osm4choc3DS0SI, osm1choc12T1SI,
                 osm12ct3T1, osm24t3e3,
                 osm2oc12AtmMMPlus, osm2oc12AtmSIPlus,
                 osm8oc3PosSLPlus, wsx6516aGbic,
                 wsx6148getx, wsSvcWlan1k9,
                 wsSvcAon1k9, wsx6148FeSfp,
                 wsx65822pa

                 Updated moduleType for name changed:
                 wsx61821pa changed to wsx61822pa

                 Updated moduleSubType to include new hardwares:
                 wsf6700dfc3a, wsf6kdfc3bxl,
                 wsf6kpfc3bxl, wsf6700dfc3bxl,
                 wsf6700dfc3b, wsf6kdfc3b

                 Updated moduleSubType to include new hardwares:
                 wssvccmm6e1, wssvccmm6t1,
                 wssvccmm24fxs, wssvccmmact

                 Updated portType to include:
                 e10GBaseWdm1550, e10GBaseLW,
                 e10GBaseEW, lwa,
                 aons, e100BaseEmpty,
                 e100BaseUnknown, e100BaseUnapproved,
                 e100BaseSX, e100BaseBX10D,
                 e100BaseBX10U, e1000BaseBX10D,
                 e1000BaseBX10U, e10GBaseBad

                 Updated portType for name changed:
                 posOc48mm changed to posOc48sms

                 Modified ipPermitAccessType, ipPermitDeniedAccess,
                 ipPermitAccessTypeEnable to include:
                 http

                 Modified syslogMessageFacility to include:
                 diags

                 Modified portCpbInlinePower to include:
                 static

                 Deprecated sysEnableStpxTrap, replaced by
                       stpxNotificationEnable in
                       CISCO-STP-EXTENSIONS-MIB.my

                 Deprecated radiusServerTable, replaced by
                       crRadiusServerTable in CISCO-RADIUS-MIB.my

                 Added new conformance Groups:
                 optionalSystemTrapGroup1,
                 authenticationGroup2,
                 systemTrapGroup2,
                 notificationGroup."

        REVISION "200405140000Z"
        DESCRIPTION
                "Modified sysEnableBridgeTraps to include:
                 'enabledForNewRootOnly' and 'enabledForTopoChangeOnly'

                 Updated moduleType for new hardwares:
                 wsx2948ggetx, wsx2948ggetxgbrj and wsx6748sfp

                 Updated moduleSubType for the new harware:
                 wsf6kpfc3b

                 Updated moduleSubType2 for the new harware:
                 wsf6kVpwrGe

                 Updated portType to include:
                 e10GBaseSR, e10GBaseCX4,
                 e1000BaseUnknown and e10GBaseUnknown,
                 e10GBaseUnapproved, e1000BaseWdmRxOnly,
                 e1000BaseDwdm3033,e1000BaseDwdm3112,
                 e1000BaseDwdm3190,e1000BaseDwdm3268,
                 e1000BaseDwdm3425,e1000BaseDwdm3504,
                 e1000BaseDwdm3582,e1000BaseDwdm3661,
                 e1000BaseDwdm3819,e1000BaseDwdm3898,
                 e1000BaseDwdm3977,e1000BaseDwdm4056,
                 e1000BaseDwdm4214,e1000BaseDwdm4294,
                 e1000BaseDwdm4373,e1000BaseDwdm4453,
                 e1000BaseDwdm4612,e1000BaseDwdm4692,
                 e1000BaseDwdm4772,e1000BaseDwdm4851,
                 e1000BaseDwdm5012,e1000BaseDwdm5092,
                 e1000BaseDwdm5172,e1000BaseDwdm5252,
                 e1000BaseDwdm5413,e1000BaseDwdm5494,
                 e1000BaseDwdm5575,e1000BaseDwdm5655,
                 e1000BaseDwdm5817,e1000BaseDwdm5898,
                 e1000BaseDwdm5979,e1000BaseDwdm6061,
                 e10GBaseWdmRxOnly, e10GBaseDwdm3033,
                 e10GBaseDwdm3112, e10GBaseDwdm3190
                 e10GBaseDwdm3268, e10GBaseDwdm3425,
                 e10GBaseDwdm3504, e10GBaseDwdm3582,
                 e10GBaseDwdm3661, e10GBaseDwdm3819,
                 e10GBaseDwdm3898, e10GBaseDwdm3977,
                 e10GBaseDwdm4056, e10GBaseDwdm4214,
                 e10GBaseDwdm4294, e10GBaseDwdm4373,
                 e10GBaseDwdm4453, e10GBaseDwdm4612,
                 e10GBaseDwdm4692, e10GBaseDwdm4772,
                 e10GBaseDwdm4851, e10GBaseDwdm5012,
                 e10GBaseDwdm5092, e10GBaseDwdm5172,
                 e10GBaseDwdm5252, e10GBaseDwdm5413,
                 e10GBaseDwdm5494, e10GBaseDwdm5575,
                 e10GBaseDwdm5655, e10GBaseDwdm5817,
                 e10GBaseDwdm5898, e10GBaseDwdm5979 and
                 e10GBaseDwdm6061

                 Modified portAdminSpeed to include:
                 'autoDetect10100'

                 Modified syslogMessageFacility to include:
                 'dhcpsnooping'."

        REVISION "200401150000Z"
        DESCRIPTION
                "Updated workgroup for new hardware:
                 wsc2948ggetxsysID

                 Updated chassisSysType for new hardware:
                 wsc2948ggetx

                 Updated chassisPs1Type for new hardware:
                 w156

                 Updated moduleType for new hardwares:
                 wsx4148lxmt, wsx4548gbrj45, wsx4548gbrj45v
                 wsx4248rj21v, wsx4302gb, wsx4248rj45v, wsx6748getx,
                 wsx670410ge, wsx6724sfp and wsx6148x2rj45

                 Updated moduleSubType2 for new hardwares:
                 wsf6kmsfc, wsf6kmsfc2, wsf6kmsfc2a,
                 wsf6kFe48af, wsf6kGe48af and wsf6kFe48x2af,

                 Updated moduleType for new hardwares:
                 e1000BaseUnknown and e10GBaseUnknown.

                 Modified syslogMessageFacility to include 'callhome'.

                 Modified sysErrDisableTimeoutEnable to include
                 'arpInspectionRate' and 'noStaticInlinePwr'.

                 Modified Description clause for deprecated objects:
                 sysIpAddr, sysNetMask, sysBroadcast, sysReset,
                 sysConsolePrimaryLoginAuthentication,
                 sysConsolePrimaryEnableAuthentication,
                 sysTelnetPrimaryLoginAuthentication,
                 sysTelnetPrimaryEnableAuthentication,
                 sysPortFastBpduGuard, chassisSerialNumber,
                 chassisComponentTable, moduleSerialNumber,
                 moduleHwHiVersion, moduleHwLoVersion,
                 moduleFwHiVersion, moduleFwLoVersion,
                 moduleSwHiVersion, moduleSwLoVersion,
                 portSpantreeFastStart, monitorGrp and
                 vlanSpantreeEnable.

                 Added new conformance Groups:
                 systemMiscGroup1,
                 systemTrapGroup1,
                 optionalSystemMiscGroup6,
                 optionalChassisGroup1,
                 portGroup4,
                 vlanGroup2,
                 ipPermitGroup2 and
                 optionalPortGroup1."

        REVISION "200305290000Z"
        DESCRIPTION
                "Change the ORGANIZATION clause. Deprecated
                 sysClearMacTime object."
        REVISION
                "200305050000Z"
        DESCRIPTION
                "Add support of the following objects: cisco7613sysID,
                 wsc6509nebasysID. ChassisType: wsc4507, wsc6509NEBA,
                 wsc65509, cisco7613. chassisPs1Type: pwr950dc,
                 pwr1900ac, pwr1900dc, wscac3000w,
                 pwrc451400dcp, wscdc3000w, pwr1400ac.
                 chassisPs2Type: pwr950dc, pwr1900ac, pwr1900dc,
                 wscac3000w,  wscdc3000w, pwr1400ac.
                 moduleTable: wsSvcIdsm2, wsSvcFwm1, wsSvcCe1,
                 wssvcSsl1, osm2oc12PosMMPlus, osm2oc12PosSIPlus,
                 osm16oc3PosSIPlus, osm1oc48PosSSPlus,osm1oc48PosSIPlus,
                 osm1oc48PosSLPlus, osm4oc3PosSIPlus, osm8oc3PosSIPlus,
                 osm4oc12PosSIPlus, wsx6548getx, wssup720, wssup720base.
                 moduleSubType: wsf6kpfc2a, wsf6kdfca, vsp300dfc,
                 wsf6kpfc3a, wsf6kdfc3a. moduleSubType2: wsg6489,
                 wsg6485, wsu4502gb, wssvcidsupg, wssup720.
                 portType: e100BaseLX.

                 Deprecate the following objects: sysIpAddr, sysNetMask,
                 sysBroadcast, sysTrapReceiverTable, sysReset,
                 sysClearPortTime, sysClearMacTime,
                 sysPortFastBpduGuard, chassisComponentTable,
                 portSpantreeFastStart, vlanTable, portChannelTable.

                 Remove the TC MacAddressType, and replaced other uses
                 by MacAddress."

        REVISION
                "200209240000Z"
        DESCRIPTION
                "Added more HW models."
        REVISION
                "200106110000Z"
        DESCRIPTION
                "Added cat6000 new HW chassis & modules."
        REVISION
                "200104110000Z"
        DESCRIPTION
                "Added more HW modules;
                 Added the following MIB objects under systemGrp:
                        sysMaxRmonMemory
                        sysMacReductionAdminEnable
                        sysMacReductionOperEnable
                 Added the following MIB object under fileCopyGrp:
                        fileCopyRuntimeConfigPart
                 Added the following MIB object under filterPortTable:
                        filterPortSuppressionOption
                 Added the following MIB object under syslogGrp:
                        syslogTelnetEnable"

        REVISION
                "200010100000Z"
        DESCRIPTION
                "Added more HW modules;
                 Added the following objects in systemGrp
                     sshPublicKeySize
                 Added the vlanTrunkMappingTable in vlanGrp
                 Added portJumboFrameGrp
                 Added the following objects in portCpbTable:
                        portCpbCosRewrite
                        portCpbTosRewrite
                        portCpbCopsGrouping
                 Added copyTechReportFromRuntimeToHost in fileCopyAction
                 Added ssh(2) in ipPermitAccessType &
                 ipPermitDeniedAccess."

        REVISION
                "200005160000Z"
        DESCRIPTION
                "Added more HW models;
                 Added the following objects:
                        portInlinePowerDetect
                        vlanPortAuxiliaryVlan
                        portCpbInlinePower
                        portCpbAuxiliaryVlan
                        moduleAdditionalStatus
                        sysExtendedRmonNetflowModuleMask
                 Added the voiceGrp
                 Added the switchAccelerationGrp"

        REVISION
                "200002020000Z"
        DESCRIPTION
                "Added the following objects:
                        sysPortFastBpduGuard
                        sysErrDisableTimeoutEnable
                        sysErrDisableTimeoutInterval
                        sysTrafficMonitorHighWaterMark
                        chassisPs3Type
                        chassisPs3Status
                        chassisPs3TestResult
                        chassisPEMInstalled
                        moduleEntPhysicalIndex
                        portAdditionalOperStatus
                        portEntPhysicalIndex
                        filterPortBroadcastThresholdFraction
                        mcastEnableRgmp
                        portCpbSpan.
                 modified ipPermitGrp for supporting IP Permit
                 Enhancement. Added more HW models."

        REVISION
                "9909300000Z"
        DESCRIPTION
            "Added more HW models."

        REVISION
                "9903260000Z"
        DESCRIPTION
            "Added traceRouteGrp."

        REVISION
                "9902120000Z"
        DESCRIPTION
            "Initial v2 version of this MIB module."
        ::= { workgroup 1 }

adapterCard         OBJECT IDENTIFIER ::= { workgroup 2 }
wsc1000sysID        OBJECT IDENTIFIER ::= { workgroup 3 }
wsc1100sysID        OBJECT IDENTIFIER ::= { workgroup 4 }
wsc1200sysID        OBJECT IDENTIFIER ::= { workgroup 5 }
wsc1400sysID        OBJECT IDENTIFIER ::= { workgroup 6 }
wsc5000sysID        OBJECT IDENTIFIER ::= { workgroup 7 }
wsc1600sysID        OBJECT IDENTIFIER ::= { workgroup 8 }
cpw1600sysID        OBJECT IDENTIFIER ::= { workgroup 9 }
wsc3000sysID        OBJECT IDENTIFIER ::= { workgroup 10 }
-- rhino            OBJECT IDENTIFIER ::= { workgroup 11 }
wsc2900sysID        OBJECT IDENTIFIER ::= { workgroup 12 }
cpw2200sysID        OBJECT IDENTIFIER ::= { workgroup 13 }
esStack             OBJECT IDENTIFIER ::= { workgroup 14 }
wsc3200sysID        OBJECT IDENTIFIER ::= { workgroup 15 }
cpw1900sysID        OBJECT IDENTIFIER ::= { workgroup 16 }
wsc5500sysID        OBJECT IDENTIFIER ::= { workgroup 17 }
wsc1900sysID        OBJECT IDENTIFIER ::= { workgroup 18 }
cpw1220sysID        OBJECT IDENTIFIER ::= { workgroup 19 }
wsc2820sysID        OBJECT IDENTIFIER ::= { workgroup 20 }
cpw1420sysID        OBJECT IDENTIFIER ::= { workgroup 21 }
dcd                 OBJECT IDENTIFIER ::= { workgroup 22 }
wsc3100sysID        OBJECT IDENTIFIER ::= { workgroup 23 }
cpw1800sysID        OBJECT IDENTIFIER ::= { workgroup 24 }
cpw1601sysID        OBJECT IDENTIFIER ::= { workgroup 25 }
wsc3001sysID        OBJECT IDENTIFIER ::= { workgroup 26 }
cpw1220csysID       OBJECT IDENTIFIER ::= { workgroup 27 }
wsc1900csysID       OBJECT IDENTIFIER ::= { workgroup 28 }
wsc5002sysID        OBJECT IDENTIFIER ::= { workgroup 29 }
cpw1220isysID       OBJECT IDENTIFIER ::= { workgroup 30 }
wsc1900isysID       OBJECT IDENTIFIER ::= { workgroup 31 }
tsStack             OBJECT IDENTIFIER ::= { workgroup 32 }
wsc3900sysID        OBJECT IDENTIFIER ::= { workgroup 33 }
wsc5505sysID        OBJECT IDENTIFIER ::= { workgroup 34 }
wsc2926sysID        OBJECT IDENTIFIER ::= { workgroup 35 }
wsc5509sysID        OBJECT IDENTIFIER ::= { workgroup 36 }
wsc3920sysID        OBJECT IDENTIFIER ::= { workgroup 37 }
wsc6006sysID        OBJECT IDENTIFIER ::= { workgroup 38 }
wsc6009sysID        OBJECT IDENTIFIER ::= { workgroup 39 }
wsc4003sysID        OBJECT IDENTIFIER ::= { workgroup 40 }
wsc4912gsysID       OBJECT IDENTIFIER ::= { workgroup 41 }
wsc2948gsysID       OBJECT IDENTIFIER ::= { workgroup 42 }
wsc6509sysID        OBJECT IDENTIFIER ::= { workgroup 44 }
wsc6506sysID        OBJECT IDENTIFIER ::= { workgroup 45 }
wsc4006sysID        OBJECT IDENTIFIER ::= { workgroup 46 }
wsc6509nebsysID     OBJECT IDENTIFIER ::= { workgroup 47 }
wsc6knamsysID       OBJECT IDENTIFIER ::= { workgroup 48 }
wsc2980gsysID       OBJECT IDENTIFIER ::= { workgroup 49 }
wsc6513sysID        OBJECT IDENTIFIER ::= { workgroup 50 }
wsc2980gasysID      OBJECT IDENTIFIER ::= { workgroup 51 }
cisco7603sysID      OBJECT IDENTIFIER ::= { workgroup 53 }
cisco7606sysID      OBJECT IDENTIFIER ::= { workgroup 54 }
cisco7609sysID      OBJECT IDENTIFIER ::= { workgroup 55 }
wsc6503sysID        OBJECT IDENTIFIER ::= { workgroup 56 }
wsc4503sysID        OBJECT IDENTIFIER ::= { workgroup 58 }
wsc4506sysID        OBJECT IDENTIFIER ::= { workgroup 59 }
cisco7613sysID      OBJECT IDENTIFIER ::= { workgroup 60 }
wsc6509nebasysID    OBJECT IDENTIFIER ::= { workgroup 61 }
wsc2948ggetxsysID   OBJECT IDENTIFIER ::= { workgroup 62 }
cisco7604sysID      OBJECT IDENTIFIER ::= { workgroup 63 }
wsc6504esysID       OBJECT IDENTIFIER ::= { workgroup 64 }
wsc1900LiteFxsysID  OBJECT IDENTIFIER ::= { workgroup 175 }

-- stackMIBobjects
systemGrp           OBJECT IDENTIFIER ::= { ciscoStackMIB 1 }
chassisGrp          OBJECT IDENTIFIER ::= { ciscoStackMIB 2 }
moduleGrp           OBJECT IDENTIFIER ::= { ciscoStackMIB 3 }
portGrp             OBJECT IDENTIFIER ::= { ciscoStackMIB 4 }
tftpGrp             OBJECT IDENTIFIER ::= { ciscoStackMIB 5 }
brouterGrp          OBJECT IDENTIFIER ::= { ciscoStackMIB 6 }
filterGrp           OBJECT IDENTIFIER ::= { ciscoStackMIB 7 }
monitorGrp          OBJECT IDENTIFIER ::= { ciscoStackMIB 8 }
vlanGrp             OBJECT IDENTIFIER ::= { ciscoStackMIB 9 }
securityGrp         OBJECT IDENTIFIER ::= { ciscoStackMIB 10 }
tokenRingGrp        OBJECT IDENTIFIER ::= { ciscoStackMIB 11 }
multicastGrp        OBJECT IDENTIFIER ::= { ciscoStackMIB 12 }
dnsGrp              OBJECT IDENTIFIER ::= { ciscoStackMIB 13 }
syslogGrp           OBJECT IDENTIFIER ::= { ciscoStackMIB 14 }
ntpGrp              OBJECT IDENTIFIER ::= { ciscoStackMIB 15 }
tacacsGrp           OBJECT IDENTIFIER ::= { ciscoStackMIB 16 }
ipPermitListGrp     OBJECT IDENTIFIER ::= { ciscoStackMIB 17 }
portChannelGrp      OBJECT IDENTIFIER ::= { ciscoStackMIB 18 }
portCpbGrp          OBJECT IDENTIFIER ::= { ciscoStackMIB 19 }
portTopNGrp         OBJECT IDENTIFIER ::= { ciscoStackMIB 20 }
mdgGrp              OBJECT IDENTIFIER ::= { ciscoStackMIB 21 }
radiusGrp           OBJECT IDENTIFIER ::= { ciscoStackMIB 22 }
traceRouteGrp       OBJECT IDENTIFIER ::= { ciscoStackMIB 24 }
fileCopyGrp         OBJECT IDENTIFIER ::= { ciscoStackMIB 25 }
voiceGrp            OBJECT IDENTIFIER ::= { ciscoStackMIB 26 }
portJumboFrameGrp   OBJECT IDENTIFIER ::= { ciscoStackMIB 27 }
switchAccelerationGrp OBJECT IDENTIFIER ::= { ciscoStackMIB 28 }
configGrp           OBJECT IDENTIFIER ::= { ciscoStackMIB 29 }

-- textual conventions

-- The vendor ID portion of a MacAddress (first 3 octets
-- of the 6-octet MAC address)
VendorIdType ::= TEXTUAL-CONVENTION
       STATUS          current
       DESCRIPTION     "Vendor ID Type"
       SYNTAX          OCTET STRING (SIZE (3))

-- the system group

-- Implementation of the system group is current for all Cisco Workgroup
-- Stack products.

sysMgmtType OBJECT-TYPE
        SYNTAX        INTEGER {
                        other(1),  -- none of the following
                        snmpV1(2), -- Simple Network Management Protocol
                        smux(3),   -- SNMP MUX sub-agent
                        snmpV2V1(4), -- Bi-lingual SNMP, Ver 2 and 1
                        snmpV2cV1(5),-- Bi-lingual SNMP, V2c and V1
                        snmpV3V2cV1(6) -- SNMPv3, SNMPv2c and SNMPv1
                              }
        MAX-ACCESS    read-only
        STATUS        current
        DESCRIPTION   "Type of network management running on this
                       entity."
        ::= { systemGrp 1 }

sysIpAddr OBJECT-TYPE
        SYNTAX        IpAddress
        MAX-ACCESS    read-write
        STATUS        deprecated
        DESCRIPTION   "This entity's IP address.

                      This object is deprecated and replaced by
                      ciiIPAddressType and ciiIPAddress in
                      CISCO-IP-IF-MIB."
        ::= { systemGrp 2 }

sysNetMask OBJECT-TYPE
        SYNTAX        IpAddress
        MAX-ACCESS    read-write
        STATUS        deprecated
        DESCRIPTION   "This entity's subnet mask.

                      This object is deprecated and replaced by
                      ciiIPAddressPrefixLength in CISCO-IP-IF-MIB."
        ::= { systemGrp 3 }

sysBroadcast OBJECT-TYPE
        SYNTAX        IpAddress
        MAX-ACCESS    read-write
        STATUS        deprecated
        DESCRIPTION   "This entity's broadcast address.

                      This object is deprecated and replaced by
                      ciiIPAddressBroadcast in CISCO-IP-IF-MIB."
        ::= { systemGrp 4 }

-- the trap receiver table

sysTrapReceiverTable OBJECT-TYPE
        SYNTAX        SEQUENCE OF SysTrapReceiverEntry
        MAX-ACCESS    not-accessible
        STATUS        deprecated
        DESCRIPTION   "The trap receiver table (0 to 20 entries). This
                      table lists the addresses of Network Management
                      Stations that should receive trap messages from
                      this entity when an exception condition occurs.

                      This table is deprecated and replaced by
                      trapDestTable and other tables in SNMP-TARGET-
                      MIB and SNMP-NOTIFICATION-MIB."
        ::= { systemGrp 5 }

sysTrapReceiverEntry OBJECT-TYPE
        SYNTAX        SysTrapReceiverEntry
        MAX-ACCESS    not-accessible
        STATUS        deprecated
        DESCRIPTION   "A trap receiver table entry."
        INDEX         { sysTrapReceiverAddr }
        ::= { sysTrapReceiverTable 1 }

SysTrapReceiverEntry ::=
        SEQUENCE {
                sysTrapReceiverType
                        INTEGER,
                sysTrapReceiverAddr
                        IpAddress,
                sysTrapReceiverComm
                        DisplayString
        }

sysTrapReceiverType OBJECT-TYPE
        SYNTAX        INTEGER {
                                valid(1),        -- add this entry
                                invalid(2)       -- remove this entry
                                }
        MAX-ACCESS    read-write
        STATUS        deprecated
        DESCRIPTION   "Setting this object to invalid(2) removes the
                      corresponding entry from the sysTrapReceiverTable.
                      To add a new entry to the sysTrapReceiverTable,
                      set this object to valid(1) for an IpAddress which
                      is not already in the table."
        ::= { sysTrapReceiverEntry 1 }

sysTrapReceiverAddr OBJECT-TYPE
        SYNTAX        IpAddress
        MAX-ACCESS    read-only
        STATUS        deprecated
        DESCRIPTION   "IP address for trap receiver."
        ::= { sysTrapReceiverEntry 2 }

sysTrapReceiverComm OBJECT-TYPE
        SYNTAX        DisplayString (SIZE (0..20))
        MAX-ACCESS    read-write
        STATUS        deprecated
        DESCRIPTION   "Community string used for trap messages to this
                      trap receiver."
        ::= { sysTrapReceiverEntry 3 }

-- the community table

-- This table is deprecated and replaced by the sysCommunityRo,
-- sysCommunityRw, and sysCommunityRwa objects. New workgroup products
-- will not support this table. Older products will continue to support
-- this table for some time in order to be backwards compatible with
-- existing network management applications. When this table does exist,
-- sysCommunityString.2 is the same value as sysCommunityRo,
-- sysCommunityString.3 is the same value as sysCommunityRw, and
-- sysCommunityString.4 is the same as sysCommunityRwa.

sysCommunityTable OBJECT-TYPE
        SYNTAX        SEQUENCE OF SysCommunityEntry
        MAX-ACCESS    not-accessible
        STATUS        deprecated
        DESCRIPTION   "The community table (4 entries). This table lists
                      community strings and their access levels. When an
                      SNMP message is received by this entity, the
                      community string in the message is compared with
                      this table to determine access rights of the
                      sender.

                      Note that this item is only accessible when using
                      the community string defined in sysCommunityRwa."
        ::= { systemGrp 6 }

sysCommunityEntry OBJECT-TYPE
        SYNTAX        SysCommunityEntry
        MAX-ACCESS    not-accessible
        STATUS        deprecated
        DESCRIPTION   "A community table entry."
        INDEX         { sysCommunityAccess }
        ::= { sysCommunityTable 1 }

SysCommunityEntry ::=
        SEQUENCE {
                sysCommunityAccess
                        INTEGER,
                sysCommunityString
                        DisplayString
        }

sysCommunityAccess OBJECT-TYPE
        SYNTAX        INTEGER {
                               other(1),       -- none of the following
                               readOnly(2),    -- read but not write all
                                               -- but restricted items
                               readWrite(3),   -- read and write all but
                                               -- restricted items
                               readWriteAll(4) -- read and write all
                               }
        MAX-ACCESS    read-only
        STATUS        deprecated
        DESCRIPTION   "A value of readWriteAll(4) allows the community
                      to read and write all objects in the MIB. A
                      value of readWrite(3) allows the community to
                      read and write all objects except restricted
                      items such as community strings, which cannot
                      be accessed at all. A value of readOnly(2) allows
                      the community to read all objects except
                      restricted items. A value of other(1) allows no
                      access."
        ::= { sysCommunityEntry 1 }

sysCommunityString OBJECT-TYPE
        SYNTAX        DisplayString (SIZE (0..20))
        MAX-ACCESS    read-write
        STATUS        deprecated
        DESCRIPTION   "Configurable community string with access rights
                      defined by the value of sysCommunityAccess."
        ::= { sysCommunityEntry 2 }

-- additional system group objects

sysAttachType OBJECT-TYPE
        SYNTAX        INTEGER {
                          other(1),       -- none of the following
                          dualAttach(2),  -- port 1 is A and port 2 is B
                          singleAttach(3),-- port 1 is S and port 2 is M
                          nullAttach(4),  -- port 1 is M and port 2 is M
                          dualPrio(5)     -- dual attach priority mode
                              }
        MAX-ACCESS    read-write
        STATUS        current
        DESCRIPTION   "The requested concentrator attachment type. For a
                      dual attachment concentrator which can be
                      connected to the trunk ring, the first FDDI port
                      is configured as A and the second FDDI port is
                      configured as B.
                      For a single attachment concentrator which can be
                      connected beneath another concentrator, the first
                      FDDI port is configured as M and the second FDDI
                      port is configured as S. For a null attachment
                      concentrator which can be located at the root of
                      the tree, the first two FDDI ports are configured
                      as M.
                      This object does not take effect until the
                      concentrator is reset. The current attachment
                      type can be determined from snmpFddiPORTPCType
                      for ports 1 and 2."
        DEFVAL { dualAttach }
        ::= { systemGrp 7 }

sysTraffic OBJECT-TYPE
        SYNTAX        INTEGER (0..100)
        MAX-ACCESS    read-only
        STATUS        current
        DESCRIPTION   "Traffic meter value, i.e. the percentage of
                      bandwidth utilization for the previous polling
                      interval."
        ::= { systemGrp 8 }

sysReset OBJECT-TYPE
        SYNTAX        INTEGER {
                           other(1),       -- none of the following
                           reset(2),       -- resetting the system
                           resetMinDown(3) -- reset in minimal down time
                              }
        MAX-ACCESS    read-write
        STATUS        deprecated
        DESCRIPTION   "Writing reset(2) to this object resets the
                      control logic of all modules in the system.
                      Writing resetMinDown(3) to this object resets the
                      system with the minimal system down time. The
                      resetMinDown(3) is only supported in systems with
                      redundant supervisors.

                      This object is deprecated and replaced by
                      csyScheduledReset in CISCO-SYSTEM-MIB."
        ::= { systemGrp 9 }

sysBaudRate OBJECT-TYPE
        SYNTAX        INTEGER {
                                b600(600),
                                b1200(1200),
                                b2400(2400),
                                b4800(4800),
                                b9600(9600),
                                b19200(19200),
                                b38400(38400)
                                }
        MAX-ACCESS    read-write
        STATUS        current
        DESCRIPTION   "The baud rate in bits per second of the RS-232
                      port."
        DEFVAL { b9600 }
        ::= { systemGrp 10 }

sysInsertMode OBJECT-TYPE
        SYNTAX        INTEGER {
                                other(1),       -- none of the following
                                standard(2),    -- standard insertion
                                scheduled(3),   -- scheduled insertion
                                graceful(4)     -- graceful insertion
                                }
        MAX-ACCESS    read-write
        STATUS        current
        DESCRIPTION   "The mode for inserting M-ports into the
                       concentrator ring."
        ::= { systemGrp 11 }

sysClearMacTime OBJECT-TYPE
        SYNTAX        TimeTicks
        MAX-ACCESS    read-write
        STATUS        deprecated
        DESCRIPTION   "The time (in hundredths of a second) since mac
                      counters were last cleared. Writing a 0 to this
                      object causes the mac counters to be cleared."
        ::= { systemGrp 12 }

sysClearPortTime OBJECT-TYPE
        SYNTAX        TimeTicks
        MAX-ACCESS    read-write
        STATUS        deprecated
        DESCRIPTION   "The time (in hundredths of a second) since port
                      counters were last cleared. Writing a 0 to this
                      object causes the port counters to be cleared."
        ::= { systemGrp 13 }

-- the FDDI ring map table

sysFddiRingTable OBJECT-TYPE
        SYNTAX        SEQUENCE OF SysFddiRingEntry
        MAX-ACCESS    not-accessible
        STATUS        current
        DESCRIPTION   "The fddi ring map table. This table lists the
                      nodes in the FDDI ring(s) to which the system
                      belongs."
        ::= { systemGrp 14 }

sysFddiRingEntry OBJECT-TYPE
        SYNTAX        SysFddiRingEntry
        MAX-ACCESS    not-accessible
        STATUS        current
        DESCRIPTION   "A FDDI Ring table entry."
        INDEX         { sysFddiRingSMTIndex, sysFddiRingAddress }
        ::= { sysFddiRingTable 1 }

SysFddiRingEntry ::=
        SEQUENCE {
                sysFddiRingSMTIndex
                        INTEGER,
                sysFddiRingAddress
                        MacAddress,
                sysFddiRingNext
                        MacAddress
        }

sysFddiRingSMTIndex OBJECT-TYPE
        SYNTAX        INTEGER (1..65535)
        MAX-ACCESS    read-only
        STATUS        current
        DESCRIPTION   "The value of the SMT index associated with this
                      ring."
        ::= { sysFddiRingEntry 1 }

sysFddiRingAddress OBJECT-TYPE
        SYNTAX        MacAddress -- OCTET STRING (SIZE (6))
        MAX-ACCESS    read-only
        STATUS        current
        DESCRIPTION   "The MAC address of this node in the FDDI ring."
        ::= { sysFddiRingEntry 2 }

sysFddiRingNext OBJECT-TYPE
        SYNTAX        MacAddress -- OCTET STRING (SIZE (6))
        MAX-ACCESS    read-only
        STATUS        current
        DESCRIPTION   "The MAC address of the next node in the FDDI
                       ring."
        ::= { sysFddiRingEntry 3 }

-- additional system group objects

sysEnableModem OBJECT-TYPE
        SYNTAX        INTEGER { enabled(1), disabled(2) }
        MAX-ACCESS    read-write
        STATUS        current
        DESCRIPTION   "Indicates whether the RS-232 port modem control
                      lines are enabled."
        DEFVAL { disabled }
        ::= { systemGrp 15 }

sysEnableRedirects OBJECT-TYPE
        SYNTAX        INTEGER { enabled(1), disabled(2) }
        MAX-ACCESS    read-write
        STATUS        current
        DESCRIPTION   "Indicates whether ICMP redirect messages are sent
                      or received by the system."
        DEFVAL { enabled }
        ::= { systemGrp 16 }

sysEnableRmon OBJECT-TYPE
        SYNTAX        INTEGER { enabled(1), disabled(2) }
        MAX-ACCESS    read-write
        STATUS        current
        DESCRIPTION   "Indicates whether the SNMP agent supports the
                      RMON MIB."
        DEFVAL { enabled }
        ::= { systemGrp 17 }

sysArpAgingTime OBJECT-TYPE
        SYNTAX        INTEGER (0..1000000)
        MAX-ACCESS    read-write
        STATUS        current
        DESCRIPTION   "The aging time for the ARP table."
        DEFVAL { 1200 }
        ::= { systemGrp 18 }

sysTrafficPeak OBJECT-TYPE
        SYNTAX        INTEGER (0..100)
        MAX-ACCESS    read-only
        STATUS        current
        DESCRIPTION   "Peak traffic meter value since the last time port
                      counters were cleared or the system started (see
                      sysClearPortTime)."
        ::= { systemGrp 19 }

sysTrafficPeakTime OBJECT-TYPE
        SYNTAX        TimeTicks
        MAX-ACCESS    read-only
        STATUS        current
        DESCRIPTION   "The time (in hundredths of a second) since the
                      peak traffic meter value occurred."
        ::= { systemGrp 20 }

sysCommunityRwa OBJECT-TYPE
        SYNTAX        DisplayString (SIZE (0..20))
        MAX-ACCESS    read-write
        STATUS        current
        DESCRIPTION   "When an SNMP message is received by this entity,
                      the community string in the message is compared
                      with this string first. If it matches, read-write
                      access is granted to all items in the MIB. If it
                      doesn't match, the sysCommunityRw string is
                      compared next.

                      Note that this item is only accessible when using
                      the community string defined in sysCommunityRwa."
        ::= { systemGrp 21 }

sysCommunityRw OBJECT-TYPE
        SYNTAX        DisplayString (SIZE (0..20))
        MAX-ACCESS    read-write
        STATUS        current
        DESCRIPTION   "When an SNMP message is received by this entity,
                      the community string in the message is compared
                      with this string second. If it matches, read-write
                      access is granted to all items in the MIB except
                      restricted items such as community strings.
                      (Restricted items appear empty when read and
                      return a no such name error when an attempt is
                      made to write them.)  If it doesn't match, the
                      sysCommunityRo string is compared next.

                      Note that this item is only accessible when using
                      the community string defined in sysCommunityRwa."
        ::= { systemGrp 22 }

sysCommunityRo OBJECT-TYPE
        SYNTAX        DisplayString (SIZE (0..20))
        MAX-ACCESS    read-write
        STATUS        current
        DESCRIPTION   "When an SNMP message is received by this entity,
                      the community string in the message is compared
                      with this string third. If it matches, read-only
                      access is granted to all items in the MIB except
                      restricted items such as community strings.
                      (Restricted items appear empty when read.) If it
                      doesn't match, no access is granted, no response
                      is sent back to the SNMP requester, and an SNMP
                      is sent to the SNMP trap receivers if configured.

                      Note that this item is only accessible when using
                      the community string defined in sysCommunityRwa."
        ::= { systemGrp 23 }

sysEnableChassisTraps OBJECT-TYPE
        SYNTAX        INTEGER { enabled(1), disabled(2) }
        MAX-ACCESS    read-write
        STATUS        current
        DESCRIPTION   "Indicates whether chassisAlarmOn and
                      chassisAlarmOff traps in this MIB should be
                      generated."
        DEFVAL { disabled }
        ::= { systemGrp 24 }

sysEnableModuleTraps OBJECT-TYPE
        SYNTAX        INTEGER { enabled(1), disabled(2) }
        MAX-ACCESS    read-write
        STATUS        current
        DESCRIPTION   "Indicates whether moduleUp and moduleDown traps
                      in this MIB should be generated."
        DEFVAL { disabled }
        ::= { systemGrp 25 }

sysEnableBridgeTraps OBJECT-TYPE
        SYNTAX        INTEGER {
                               enabled(1),
                               disabled(2),
                               enabledForNewRootOnly(3),   -- read-only
                               enabledForTopoChangeOnly(4) -- read-only
                               }
        MAX-ACCESS    read-write
        STATUS        deprecated
        DESCRIPTION   "Indicates whether newRoot and topologyChange
                      traps in the BRIDGE-MIB (RFC 1493) should be
                      generated.

                      enabled -- both newRoot and topologyChange
                                 traps are enabled.

                      disabled -- both of the newRoot and
                                 topologyChange traps are disabled.

                      enabledForNewRootOnly -- only the newRoot trap is
                                 enabled. This value is read-only.

                      enabledForTopoChangeOnly -- only the
                                 topologyChange trap is enabled. This
                                 value is read-only.

                      This object is deprecated and replaced by
                      stpxNotificationEnable in
                      CISCO-STP-EXTENSIONS-MIB."
        DEFVAL { disabled }
        ::= { systemGrp 26 }

sysIpVlan OBJECT-TYPE
        SYNTAX        VlanIndex
        MAX-ACCESS    read-write
        STATUS        current
        DESCRIPTION   "This entity's IP address Virtual LAN
                      association."
        DEFVAL { 1 }
        ::= { systemGrp 27 }

sysConfigChangeTime OBJECT-TYPE
        SYNTAX        TimeTicks
        MAX-ACCESS    read-only
        STATUS        current
        DESCRIPTION   "The time (in hundredths of a second) since the
                      configuration of the system was last changed."
        ::= { systemGrp 28 }

sysEnableRepeaterTraps OBJECT-TYPE
        SYNTAX        INTEGER { enabled(1), disabled(2) }
        MAX-ACCESS    read-write
        STATUS        current
        DESCRIPTION   "Indicates whether the traps in the REPEATER-MIB
                      (RFC1516) should be generated."
        DEFVAL { disabled }
        ::= { systemGrp 29 }

sysBannerMotd OBJECT-TYPE
        SYNTAX        DisplayString (SIZE (0..255))
        MAX-ACCESS    read-write
        STATUS        current
        DESCRIPTION   "Message of the day banner which is displayed on
                      the Command Line Interface before log in."
        ::= { systemGrp 30 }

sysEnableIpPermitTraps OBJECT-TYPE
        SYNTAX        INTEGER { enabled(1), disabled(2) }
        MAX-ACCESS    read-write
        STATUS        current
        DESCRIPTION   "Indicates whether the IP permit traps in this MIB
                       should be generated."
        DEFVAL { disabled }
        ::= { systemGrp 31 }

-- the system traffic meter table

sysTrafficMeterTable OBJECT-TYPE
        SYNTAX        SEQUENCE OF SysTrafficMeterEntry
        MAX-ACCESS    not-accessible
        STATUS        current
        DESCRIPTION   "The system traffic meter table. This table
                      lists the traffic meters available in the
                      system."
        ::= { systemGrp 32 }

sysTrafficMeterEntry OBJECT-TYPE
        SYNTAX        SysTrafficMeterEntry
        MAX-ACCESS    not-accessible
        STATUS        current
        DESCRIPTION   "A traffic meter table entry."
        INDEX         { sysTrafficMeterType}
        ::= { sysTrafficMeterTable 1 }

SysTrafficMeterEntry ::=
        SEQUENCE {
                sysTrafficMeterType
                        INTEGER,
                sysTrafficMeter
                        INTEGER,
                sysTrafficMeterPeak
                        INTEGER,
                sysTrafficMeterPeakTime
                        TimeTicks
        }

sysTrafficMeterType OBJECT-TYPE
        SYNTAX        INTEGER {
                systemSwitchingBus(1), -- system switching bus
                                       -- for WS-X5530 supervisor module
                switchingBusA(2),      -- switching bus A
                switchingBusB(3),      -- switching bus B
                switchingBusC(4)       -- switching bus C
                        }
        MAX-ACCESS    read-only
        STATUS        current
        DESCRIPTION   "The type of traffic meter."
        ::= { sysTrafficMeterEntry 1 }

sysTrafficMeter OBJECT-TYPE
        SYNTAX        INTEGER (0..100)
        MAX-ACCESS    read-only
        STATUS        current
        DESCRIPTION   "Traffic meter value, i.e. the percentage of
                      bandwidth utilization for the previous polling
                      interval."
        ::= { sysTrafficMeterEntry 2 }

sysTrafficMeterPeak OBJECT-TYPE
        SYNTAX        INTEGER (0..100)
        MAX-ACCESS    read-only
        STATUS        current
        DESCRIPTION   "Peak traffic meter value since the system
                      started."
        ::= { sysTrafficMeterEntry 3 }

sysTrafficMeterPeakTime OBJECT-TYPE
        SYNTAX        TimeTicks
        MAX-ACCESS    read-only
        STATUS        current
        DESCRIPTION   "The time (in hundredths of a second) since the
                      peak traffic meter value occurred."
        ::= { sysTrafficMeterEntry 4 }

sysEnableVmpsTraps OBJECT-TYPE
        SYNTAX        INTEGER { enabled(1), disabled(2) }
        MAX-ACCESS    read-write
        STATUS        current
        DESCRIPTION   "Indicates whether the vmVmpsChange trap defined
                      in CISCO-VLAN-MEMBERSHIP-MIB should be generated."
        DEFVAL { disabled }
        ::= { systemGrp 33}

sysConfigChangeInfo OBJECT-TYPE
        SYNTAX        DisplayString (SIZE (0..255))
        MAX-ACCESS    read-only
        STATUS        current
        DESCRIPTION   "Indicates which NVRAM block is changed by whom."
        ::= { systemGrp 34 }

sysEnableConfigTraps OBJECT-TYPE
        SYNTAX        INTEGER { enabled(1), disabled(2) }
        MAX-ACCESS    read-write
        STATUS        current
        DESCRIPTION   "Indicates whether sysConfigChange trap in this
                      MIB should be generated."
        DEFVAL { disabled }
        ::= { systemGrp 35 }

sysConfigRegister OBJECT-TYPE
        SYNTAX        OCTET STRING (SIZE (2))
        MAX-ACCESS    read-write
        STATUS        current
        DESCRIPTION   "The value of configuration register that will be
                      used by the supervisor module when the system is
                      restarted.
                      This MIB object is only supported in systems with
                      supervisor modules having ROMMON support.

                      The lowest four bits of the configuration register
                      (bits 3,2,1, and 0) form the boot field and the
                      boot field determines whether the system boots
                      from as the following:
                      0000  -- stay in ROM monitor
                      0001  -- boot from the first bootable system
                               images on the bootflash
                      0010 to 1111
                            -- boot from the first bootable system
                               images specified in the sysBootVariable

                      The bit 5(0x0020) indicates whether the
                      configuration file specified in
                      sysStartupConfigSourceFile will beused recurringly
                      or not whenever the system resets. If this bit is
                      not set, the configuration file(s) specified in
                      sysStartupConfigSourceFile will only be used once
                      and the value of sysStartupConfigSourceFile will
                      be reset to empty string automatically during the
                      next system reset.

                      If the bit 6(0x0040) is set, the system will start
                      with default configuration.

                      The bits 11,12 (0x0800, 0x1000) are used to
                      specify the console line speed in ROM monitor mode
                      as the following:
                      00   -- 9600
                      01   -- 1200
                      10   -- 4800
                      11   -- 2400

                      The unspecified bits are not used."
        DEFVAL { '010f'h } -- "01 0F"
        ::= { systemGrp 36 }

sysBootVariable OBJECT-TYPE
        SYNTAX        DisplayString (SIZE (0..255))
        MAX-ACCESS    read-write
        STATUS        current
        DESCRIPTION   "A list of the system boot images in the BOOT
                      environment variable on supervisor modules with
                      ROMMON. The format of sysBootVariable should be:
                   <device>:[<fileName>],1;{<device>:[<fileName>],1;...}
                      If the [fileName] is not specified, the first file
                      on the <device> will be used.

                      This MIB object is only supported in systems
                      having supervisor modules with ROMMON."
--      DEFVAL { "bootflash:" }
        ::= { systemGrp 37 }

sysBootedImage OBJECT-TYPE
        SYNTAX        DisplayString (SIZE (0..255))
        MAX-ACCESS    read-only
        STATUS        current
        DESCRIPTION   "The name of the system boot image which the
                      system booted from.
                      This MIB object is only supported in the system
                      with Supervisor module 3 present."
        ::= { systemGrp 38 }

sysEnableEntityTrap OBJECT-TYPE
        SYNTAX        INTEGER { enabled(1), disabled(2) }
        MAX-ACCESS    read-write
        STATUS        current
        DESCRIPTION   "Indicates whether entConfigChange trap in the
                      ENTITY-MIB should be generated."
        DEFVAL { disabled }
        ::= { systemGrp 39 }

sysEnableStpxTrap OBJECT-TYPE
        SYNTAX        INTEGER {
                                enabled(1),
                                disabled(2),
                                enabledForInconOnly(3),     -- read-only
                                enabledForRootOnly(4),      -- read-only
                                enabledForLoopOnly(5),      -- read-only
                                enabledForInconRootOnly(6), -- read-only
                                enabledForInconLoopOnly(7), -- read-only
                                enabledForRootLoopOnly(8)   -- read-only
                              }
        MAX-ACCESS    read-write
        STATUS        deprecated
        DESCRIPTION   "Indicates whether stpxInconsistencyUpdate,
                      stpxRootInconsistencyUpdate and
                      stpxLoopInconsistencyUpdate notifications in
                      CISCO-STP-EXTENSIONS-MIB should be generated.

                      enabled -- the stpxInconsistencyUpdate,
                                 stpxRootInconsistencyUpdate and
                                 stpxLoopInconsistencyUpdate traps are
                                 all enabled.

                      disabled -- the stpxInconsistencyUpdate,
                                 stpxRootInconsistencyUpdate and
                                 stpxLoopInconsistencyUpdate traps
                                 are all disabled.

                      enabledForInconOnly -- only the
                                 stpxInconsistencyUpdate trap is
                                 enabled. This value is read-only.

                      enabledForRootOnly -- only the
                                 stpxRootInconsistencyUpdate trap is
                                 enabled. This value is read-only.

                      enabledForLoopOnly -- only the
                                 stpxLoopInconsistencyUpdate trap is
                                 enabled. This value is read-only.

                      enabledForInconRootOnly -- only the
                                 stpxInconsistencyUpdate and
                                 stpxRootInconsistencyUpdate traps are
                                 enabled. This value is read-only.

                      enabledForInconLoopOnly -- only the
                                 stpxInconsistencyUpdate and
                                 stpxLoopInconsistencyUpdate traps are
                                 enabled. This value is read-only.

                      enabledForRootLoopOnly -- only the
                                 stpxRootInconsistencyUpdate and
                                 stpxLoopInconsistencyUpdate traps are
                                 enabled. This value is read-only.

                      This object is deprecated and replaced by
                      stpxNotificationEnable in
                      CISCO-STP-EXTENSIONS-MIB."
        DEFVAL { disabled }
        ::= { systemGrp 40 }

sysExtendedRmonVlanModeEnable OBJECT-TYPE
        SYNTAX        INTEGER { enabled(1), disabled(2) }
        MAX-ACCESS    read-write
        STATUS        current
        DESCRIPTION   "Indicates whether the Extended RMON VlanMode
                      feature is enabled or not. If it is set to
                      enabled(1), hostTable (rmon 4) will provide the
                      information of a list of VLANs instead of a list
                      of MAC addresses for a monitored trunking port."
        DEFVAL { disabled }
        ::= { systemGrp 41 }

sysExtendedRmonNetflowPassword OBJECT-TYPE
        SYNTAX        DisplayString (SIZE (0..20))
        MAX-ACCESS    read-write
        STATUS        current
        DESCRIPTION   "The password for enabling the Extended RMON
                      Netflow feature and this object has to be set
                      before setting sysExtendedRmonNetflowEnable to
                      enabled(1). When reading this object, it will
                      return empty string.

                      If the platform supports
                      sysExtendedRmonNetflowModuleMask object, this
                      object will be not be supported."
        ::= { systemGrp 42 }

sysExtendedRmonNetflowEnable OBJECT-TYPE
        SYNTAX        INTEGER { enabled(1), disabled(2) }
        MAX-ACCESS    read-write
        STATUS        current
        DESCRIPTION   "Indicates whether the Extended RMON Netflow
                      feature is enabled or not. Setting this object to
                      disabled(2), will clear
                      sysExtendedRmonNetflowPassword automatically.
                      Setting this object to enabled(1) will be rejected
                      if sysExtendedRmonNetflowPassword does not contain
                      a valid password.

                      If the platform supports
                      sysExtendedRmonNetflowModuleMask object, this
                      object will not be supported."
        DEFVAL { disabled }
        ::= { systemGrp 43 }

sysExtendedRmonVlanAgentEnable OBJECT-TYPE
        SYNTAX        INTEGER { enabled(1), disabled(2) }
        MAX-ACCESS    read-write
        STATUS        current
        DESCRIPTION   "Indicates whether the Extended RMON VlanAgent
                      feature is enabled or not. If it is set to
                      enabled(1), the extended RMON will also provide
                      the information on VLAN based interface in
                      addition to the port based interface for the
                      monitored traffic.
                      Setting this object to enabled(1), it will consume
                      more CPU for processing each monitored frame and
                      affect Extended RMON performance."
        DEFVAL { disabled }
        ::= { systemGrp 44 }

sysExtendedRmonEnable OBJECT-TYPE
        SYNTAX        INTEGER {
                      enabled(1),
                      disabled(2),
                      noNAMPresent(3) -- No Network Analysis Module
                                      -- present
                      }
        MAX-ACCESS    read-write
        STATUS        current
        DESCRIPTION   "Indicates whether the SNMP agent supports the
                      extended RMON feature. noNAMPresent(3) is a
                      read-only value and the agent will return this
                      value when the sysEnableExtendedRmon is set to
                      enabled(1), but Network Analysis module is not
                      present in the system."
        DEFVAL { enabled }
        ::= { systemGrp 45 }

sysConsolePrimaryLoginAuthentication OBJECT-TYPE
        SYNTAX        INTEGER{ tacacs(1),
                               radius(2),
                               local(3) -- read-only
                             }
        MAX-ACCESS    read-write
        STATUS        deprecated
        DESCRIPTION   "Indicates whether TACACS+ or RADIUS is the
                      primary login authentication, i.e which method
                      will be tried first for a console session. If
                      tacacsLoginAuthentication and
                      radiusLoginAuthentication are set to disabled
                      then sysConsolePrimaryLoginAuthentication will
                      have a value of local(3).

                      This object is deprecated and replaced by
                      cacPriorityTable in CISCO-AAA-CLIENT-MIB."
        ::= { systemGrp 46 }

sysConsolePrimaryEnableAuthentication OBJECT-TYPE
        SYNTAX        INTEGER{ tacacs(1),
                               radius(2),
                               local(3) -- read-only
                             }
        MAX-ACCESS    read-write
        STATUS        deprecated
        DESCRIPTION   "Indicates whether TACACS+ or RADIUS is the
                      primary enable authentication, i.e which method
                      will be  tried first for a console session. If
                      tacacsEnableAuthentication and
                      radiusEnableAuthentication are set to disabled
                      then sysConsolePrimaryEnableAuthentication will
                      have a value of local(3).

                      This object is deprecated and replaced by
                      cacPriorityTable in CISCO-AAA-CLIENT-MIB."
        ::= { systemGrp 47 }

sysTelnetPrimaryLoginAuthentication OBJECT-TYPE
        SYNTAX        INTEGER{ tacacs(1),
                               radius(2),
                               local(3) -- read-only
                             }
        MAX-ACCESS    read-write
        STATUS        deprecated
        DESCRIPTION   "Indicates whether TACACS+ or RADIUS is the
                      primary login authentication, i.e which method
                      will be  tried first for a telnet session. If
                      tacacsLoginAuthentication and
                      radiusLoginAuthentication are set to disabled then
                      sysTelnetPrimaryLoginAuthentication will have a
                      value of local(3).

                      This object is deprecated and replaced by
                      cacPriorityTable in CISCO-AAA-CLIENT-MIB."
        ::= { systemGrp 48 }

sysTelnetPrimaryEnableAuthentication OBJECT-TYPE
        SYNTAX        INTEGER{ tacacs(1),
                               radius(2),
                               local(3) -- read-only
                             }
        MAX-ACCESS    read-write
        STATUS        deprecated
        DESCRIPTION   "Indicates whether TACACS+ or RADIUS is the
                      primary enable authentication, i.e which method
                      will be tried first for a telnet session. If
                      tacacsEnableAuthentication and
                      radiusEnableAuthentication are set to disabled
                      then sysTelnetPrimaryEnableAuthentication will
                      have a value of local(3).

                      This object is deprecated and replaced by
                      cacPriorityTable in CISCO-AAA-CLIENT-MIB."
        ::= { systemGrp 49 }

sysStartupConfigSource OBJECT-TYPE
        SYNTAX        INTEGER{ flashFileRecurring(1),
                               flashFileNonRecurring(2)
                             }
        MAX-ACCESS    read-write
        STATUS        current
        DESCRIPTION   "Indicates whether the configuration file(s)
                      specified in sysStartupConfigSourceFile will be
                      used recurringly or not whenever the system
                      resets.
                      Setting this object to flashFileNonRecurring(2),
                      the configuration file(s) specified in
                      sysStartupConfigSourceFile will only be used once
                      and the value of sysStartupConfigSourceFile will
                      be reset to empty string automatically during the
                      next system reset.

                      This MIB object is only supported in systems with
                      SupG supervisor models or supervisor models that
                      have flash file system support."
        ::= { systemGrp 50 }

sysStartupConfigSourceFile OBJECT-TYPE
        SYNTAX        DisplayString
        MAX-ACCESS    read-write
        STATUS        current
        DESCRIPTION   "Indicates which configuration file(s) on the
                      flash device will be used during the next system
                      startup.
                      If the value of this MIB object contains one or
                      multiple valid configuration file(s), then the
                      valid configuration file(s) will reconfigure the
                      system during the next system startup one by one
                      in the order specified. If the value of this MIB
                      object does not contain the valid configuration
                      file(s) on the device, the NVRAM configuration
                      will be used instead.

                      For supervisor models wsx5540 and wsx5550, only
                      'cfg1' and 'cfg2' are valid file names.

                      For supervisor models with the flash file system
                      support, the valid file name has the format of
                      '<device:><file>[;<device:><file>...]'.

                      This MIB object is only supported in systems with
                      supervisor models wsx5540 and wsx5550 or
                      supervisor models with the flash file system
                      support."
        ::= { systemGrp 51 }

sysConfigSupervisorModuleNo OBJECT-TYPE
        SYNTAX        INTEGER (1..16)
        MAX-ACCESS    read-write
        STATUS        current
        DESCRIPTION   "Indicates the supervisor module (active or
                      standby, if applicable) that the MIB objects
                      sysConfigRegister, sysBootVariable,
                      sysStartupConfigSource, and
                      sysStartupConfigSourceFile are specified for.

                      This MIB object is only supported by the
                      supervisor modules with the flash file system
                      feature support. The default value for this MIB
                      object is set to the active supervisor module
                      number."
         ::= { systemGrp 52 }

sysStandbyPortEnable OBJECT-TYPE
        SYNTAX        INTEGER {
                      enabled(1),
                      disabled(2)

                      }
        MAX-ACCESS    read-write
        STATUS        current
        DESCRIPTION   "Indicates whether the standby port feature is
                      enabled or not. If this object is set to
                      enabled(1), the uplink ports on the standby
                      supervisor module are activated; otherwise, the
                      uplink ports on the standby supervisor remain
                      inactive."
        DEFVAL {disabled }
        ::= { systemGrp 53 }

sysPortFastBpduGuard OBJECT-TYPE
        SYNTAX        INTEGER {
                      enabled(1),
                      disabled(2)
                      }
        MAX-ACCESS    read-write
        STATUS        deprecated
        DESCRIPTION   "Indicates whether BPDU Guard for Spanning Tree
                      Port Fast Start feature is enabled or not. If the
                      value of this object is set to enabled(1), then
                      when the switch receives a BPDU from a port with
                      the value of portSpantreeFastStart object set to
                      enabled(1), that port is immediately disabled.

                      This object is deprecated and replaced by
                      stpxFastStartBpduGuardEnable in
                      CISCO-STP-EXTENSIONS-MIB."
        DEFVAL { disabled }
        ::= { systemGrp 54 }

sysErrDisableTimeoutEnable OBJECT-TYPE
        SYNTAX        BITS {
                             other(0),
                             udld(1),
                             duplexMismatch(2),
                             bpduPortGuard(3),
                             channelMisconfig(4),
                             crossBarFallBack(5),
                             gl2ptIngressLoop(6),
                             gl2ptThresholdExceed(7),
                             bcastSuppression(8),
                             arpInspectionRate(9),
                             noStaticInlinePwr(10),
                             camMonitor(11),
                             gl2ptCdpThresholdExceed(12),
                             gl2ptStpThresholdExceed(13),
                             gl2ptVtpThresholdExceed(14),
                             linkRxCrc(15),
                             linkTxCrc(16),
                             linkInErrors(17),
                             packetBufferError(18),
                             ethernetOam(19),
                             gl2ptEoamThresholdExceed(20)
                           }
        MAX-ACCESS    read-write
        STATUS        current
        DESCRIPTION   "Indicates whether errdisable timeout feature is
                      enabled for each of the causes or not. The
                      other(0) is for all causes other than:
                      udld(1),
                      duplexMismatch(2),
                      bpduPortGuard(3),
                      channelMisconfig(4),
                      crossBarFallBack(5), (only supported on platforms
                                            that support this errdisable
                                            reason.)
                      gl2ptIngressLoop(6), (only supported on platforms
                                            that support this errdisable
                                            reason.)
                      gl2ptThresholdExceed(7), (only supported on
                                            platforms that support this
                                            errdisable reason.)
                      bcastSuppression(8), (only supported on platforms
                                            that support this errdisable
                                            reason.)
                      arpInspectionRate(9), (only supported on platforms
                                            that support this errdisable
                                            reason.)
                      noStaticInlinePwr(10), (only supported on
                                             platforms that support this
                                             errdisable reason.)
                      camMonitor(11),       (only supported on
                                             platforms that support this
                                             errdisable reason.)
                      gl2ptCdpThresholdExceed(12), (only supported on
                                             platforms that support this
                                             errdisable reason.)
                      gl2ptStpThresholdExceed(13), (only supported on
                                             platforms that support this
                                             errdisable reason.)
                      gl2ptVtpThresholdExceed(14), (only supported on
                                             platforms that support this
                                             errdisable reason.)
                      linkRxCrc(15),        (only supported on
                                             platforms that support this
                                             errdisable reason.)
                      linkTxCrc(16),        (only supported on
                                             platforms that support this
                                             errdisable reason.)
                      linkInErrors(17),     (only supported on
                                             platforms that support this
                                             errdisable reason.)
                      packetBufferError(18), (only supported on
                                             platforms that support this
                                             errdisable reason.)
                      ethernetOam(19),       (only supported on
                                             platforms that support this
                                             errdisable reason.)
                      gl2ptEoamThresholdExceed(20), (only supported on
                                             platforms that support this
                                             errdisable reason.)

                      A port is in errdisable state if ifAdminStatus of
                      the port in the ifTable is up(1) while the port is
                      shutdown during runtime by the system due to error
                      detection. If the value of object
                      portAdditionalOperStatus for the port is
                      errdisable(11) then that port is in errdisable
                      state.

                      By setting the bit corresponding to a cause to
                      '1', this errdisable timeout feature is enabled
                      on the system for the ports that are put into
                      errdisable state by that cause, then those ports
                      can be re-enabled automatically during the timeout
                      interval as specified by
                      sysErrDisableTimeoutInterval object after they
                      are put into errdisable state by that cause;
                      otherwise, by setting the bit corresponding to a
                      cause to '0', this errdisable timeout feature is
                      disabled on the system for the ports that are put
                      into errdisable state by that cause, then those
                      ports will remain shutdown until the user
                      re-enable it manually."
        DEFVAL { { } }
        ::= { systemGrp 55 }

sysErrDisableTimeoutInterval OBJECT-TYPE
        SYNTAX        INTEGER (30..86400)
        UNITS         "seconds"
        MAX-ACCESS    read-write
        STATUS        current
        DESCRIPTION   "Indicates the timeout interval in seconds for
                      errdisable timeout feature."
        DEFVAL { 300 }
        ::= { systemGrp 56 }

sysTrafficMonitorHighWaterMark OBJECT-TYPE
        SYNTAX        INTEGER (0..100)
        MAX-ACCESS    read-write
        STATUS        current
        DESCRIPTION   "Indicates the high watermark for the switching
                      bus traffic in percentage. Syslog messages will be
                      generated if the switching bus traffic goes over
                      this object value during the polling interval.
                      Setting this object value to 100 would mean no
                      syslog message would be generated. For systems
                      with 3 switching buses, high watermark and syslog
                      will be for each switching bus."
        DEFVAL { 100 }
        ::= { systemGrp 57 }

sysHighAvailabilityEnable OBJECT-TYPE
        SYNTAX        TruthValue
        MAX-ACCESS    read-write
        STATUS        current
        DESCRIPTION   "Indicates whether High System Availability
                      feature is enabled or not. If this feature is
                      enabled, the active supervisor's layer-2 protocol
                      state will be synched to the standby supervisor
                      module, thus maintaining an up-to-date protocol
                      data on the standby supervisor whenever possible.

                      This object is supported in systems with High
                      System Availability feature support."
        DEFVAL { false }
        ::= { systemGrp 58 }

sysHighAvailabilityVersioningEnable OBJECT-TYPE
        SYNTAX        TruthValue
        MAX-ACCESS    read-write
        STATUS        current
        DESCRIPTION   "Indicates whether support for supervisor software
                      image versioning (i.e., the capability to run
                      different images on the active and standby
                      supervisors) for the High System Availability
                      feature is enabled or not.

                      This object is supported in systems with High
                      System Availability feature support."
        DEFVAL { false }
        ::= { systemGrp 59 }

sysHighAvailabilityOperStatus OBJECT-TYPE
        SYNTAX        INTEGER {
                               running(1),
                               notRunning(2)
                              }
        MAX-ACCESS    read-only
        STATUS        current
        DESCRIPTION   "Indicates the operational status of High System
                      Availability feature. If the value of this object
                      is notRunning(2), then the reason why this feature
                      is actually not running is specified by the object
                      sysHighAvailabilityNotRunningReason. If the value
                      of this object is running(1), then the value of
                      object sysHighAvailabilityOperReason is empty
                      string.

                      This object is supported in systems with High
                      System Availability feature support."
        ::= { systemGrp 60 }

sysHighAvailabilityNotRunningReason OBJECT-TYPE
        SYNTAX        DisplayString
        MAX-ACCESS    read-only
        STATUS        current
        DESCRIPTION   "Indicates the reason why High System Availability
                      feature is not running when the value of
                      sysHighAvailabilityOperStatus is notRunning(2).
                       The value of this object is empty string when
                      the value of sysHighAvailabilityOperStatus is
                      running(1).

                      This object is supported in systems with High
                      System Availability feature support."
        ::= { systemGrp 61 }

sysExtendedRmonNetflowModuleMask OBJECT-TYPE
        SYNTAX        BITS {
                                module1(0),
                                module2(1),
                                module3(2),
                                module4(3),
                                module5(4),
                                module6(5),
                                module7(6),
                                module8(7),
                                module9(8),
                                module10(9),
                                module11(10),
                                module12(11),
                                module13(12),
                                module14(13),
                                module15(14),
                                module16(15)
                       }

        MAX-ACCESS    read-write
        STATUS        current
        DESCRIPTION   "Indicates Netflow Export Data (NDE) to be sent to
                      which Network Analysis Modules (NAM) in the same
                      chassis.

                      If users set a bit from off to on, the system will
                      check the corresponding module is a NAM or not.
                      If it is not, the system should return error.

                      This mib object will only be supported by the
                      system that can support the multiple NAM modules."
        ::= { systemGrp 62 }

sshPublicKeySize OBJECT-TYPE
        SYNTAX        INTEGER (0 | 512..2048)
        MAX-ACCESS    read-write
        STATUS        current
        DESCRIPTION   "Indicates public key size in bits. In write, if
                      a key does not exist, a value between 512 and 2048
                      will generate a RSA public key with the value as
                      its key size for secured shell access. If a key
                      exists a value other than 0 is valid, indicating a
                      clear key operation. In read, the current key size
                      is returned if a key exists. If not,a 0 is
                      returned."
        ::= { systemGrp 63 }

sysMaxRmonMemory OBJECT-TYPE
        SYNTAX        INTEGER (0..100)
        MAX-ACCESS    read-write
        STATUS        current
        DESCRIPTION   "Indicates the maximum percentage of the memory
                      usage for RMON."
        ::= { systemGrp 64 }

sysMacReductionAdminEnable OBJECT-TYPE
        SYNTAX        TruthValue
        MAX-ACCESS    read-write
        STATUS        current
        DESCRIPTION   "Indicates whether Mac Reduction feature (to
                      reduce the number of MAC addresses used in
                      bridge identifier) is administratively enabled
                      on the device or not."
        ::= { systemGrp 65 }

sysMacReductionOperEnable OBJECT-TYPE
        SYNTAX        TruthValue
        MAX-ACCESS    read-only
        STATUS        current
        DESCRIPTION   "Indicates whether Mac Reduction feature (to
                      reduce the number of MAC addresses used in
                      bridge identifier) is operationaly enabled
                      on the device or not.

                      If the value of this object is true(1), then
                      the accepted values for dot1dStpPriority
                      in BRIDGE-MIB should be multiples of 4096 plus
                      bridge instance ID, such as VlanIndex. Changing
                      this object value might cause the values of
                      dot1dBaseBridgeAddress and dot1dStpPriority
                      in BRIDGE-MIB to be changed also."
        ::= { systemGrp 66 }

sysStatus OBJECT-TYPE
        SYNTAX        INTEGER {
                                other(1),       -- none of the following
                                ok(2),          -- status ok
                                minorFault(3),  -- minor problem
                                majorFault(4)   -- major problem
                                }
        MAX-ACCESS    read-only
        STATUS        current
        DESCRIPTION   "The operational status of the system."
        ::= { systemGrp 67 }

-- the chassis group

-- Implementation of the chassis group is current for all Cisco
-- Workgroup Stack products.

chassisSysType OBJECT-TYPE
        SYNTAX        INTEGER {
                      other(1),    -- none of the following
                      wsc1000(3),  -- 2+8 Port CDDI Concentrator
                      wsc1001(4),  -- 2+8 Port FDDI Concentrator
                      wsc1100(5),  -- 2+16 Port FDDI/CDDI Concentrator
                      wsc5000(6),  -- 5 slot Switch
                      wsc2900(7),  -- closed 2 slot Switch
                      wsc5500(8),  -- 13 slot Switch
                      wsc5002(9),  -- 2 slot Switch
                      wsc5505(10), -- 5 slot Switch
                      wsc1200(11), -- 2+8 Port FDDI/Ethernet Switch
                      wsc1400(12), -- 2 slot FDDI/CDDI Concentrator
                      wsc2926(13), -- closed 2 slot Switch
                      wsc5509(14), -- 9 slot Switch
                      wsc6006(15), -- 6 slot Switch
                      wsc6009(16), -- 9 slot Switch
                      wsc4003(17), -- 3 slot Switch
                      wsc5500e(18),-- 13 slot Switch
                      wsc4912g(19), -- closed 2 slot Switch
                      wsc2948g(20), -- closed 2 slot Switch
                      wsc6509(22),   -- 9 slot Switch
                      wsc6506(23),   -- 6 slot Switch
                      wsc4006(24),   -- 6 slot Switch
                      wsc6509NEB(25),-- 9 slot Verticle Chassis Switch
                      wsc2980g(26),  -- closed 3 slot Switch
                      wsc6513(27),   -- 13 slot Switch
                      wsc2980ga(28), -- closed 3 slot Switch
                      cisco7603(30), -- 3 slot Chassis (Nebula-SP)
                      cisco7606(31),  -- 6 slot Chassis (Seaquest-SP)
                      cisco7609(32),   -- 9 slot chassis
                      wsc6503(33),   -- 3 slot Chassis
                      wsc6509NEBA(34), -- 9 slot Chassis
                      wsc4507(35),   -- 7 slot Chassis (Galaxy3)
                      wsc4503(36),   -- 3 slot Chassis (Galaxy5)
                      wsc4506(37),   -- 6 slot Chassis (Galaxy6)
                      wsc65509(38),  -- 9 slot Chassis
                      cisco7613(40), -- 13 slot Chassis
                      wsc2948ggetx(41), -- closed 2 slot Switch
                      cisco7604(42), -- 4 slot Chassis
                      wsc6504e(43),  -- 4 slot Chassis
                      mec6524gs8s(45), -- closed 1 slot switch
                      mec6524gt8s(48), -- closed 1 slot switch
                      wsc6509ve(51),   -- 9 slot Chassis
                      cisco7603s(52)   -- 3 slot Chassis
                                }
        MAX-ACCESS    read-only
        STATUS        current
        DESCRIPTION   "The chassis system type."
        ::= { chassisGrp 1 }

chassisBkplType OBJECT-TYPE
        SYNTAX        INTEGER {
                                other(1),       -- none of the following
                                fddi(2),        -- FDDI
                                fddiEthernet(3),-- FDDI and Ethernet
                                giga(4),        -- 1.2 Gigabit switch
                                giga3(5),       -- 3.6 Gigabit switch
                                giga3E(6),      -- 3.6 Gigabit switch
                                                -- enhanced
                                giga12(7),      -- 12 Gigabit switch
                                giga16(8),      -- 16 Gigabit switch
                                giga40(9)        -- 40 Gigabit switch
                                }
        MAX-ACCESS    read-only
        STATUS        current
        DESCRIPTION   "The chassis backplane type."
        ::= { chassisGrp 2 }

chassisPs1Type OBJECT-TYPE
        SYNTAX        INTEGER {
                                other(1),       -- none of the following
                                none(2),        -- no power supply
                                w50(3),         -- 50 watt supply
                                w200(4),        -- 200 watt supply
                                w600(5),        -- 600 watt supply
                                w80(6),         -- 80 watt supply
                                w130(7),        -- 130 watt supply
                                wsc5008(8),     -- 376 watt supply
                                wsc5008a(9),    -- 376 watt supply w/PFC
                                w175(10),       -- 175 watt supply
                                wsc5068(11),    -- 376 watt supply DC
                                wsc5508(12),    -- 1100 watt supply
                                wsc5568(13),    -- 1200 watt supply DC
                                wsc5508a(14),   -- 1200 watt supply
                                w155(15),       -- 155 watt supply
                                w175pfc(16),    -- 175 watt supply w/PFC
                                w175dc(17),     -- 175 watt supply DC
                                wsc5008b(18),   -- 376 watt supply
                                                -- w/PFC, OCP
                                wsc5008c(19),   -- 436 watt supply w/PFC
                                wsc5068b(20),   -- 376 watt supply DC
                                                -- w/OCP
                                wscac1000(21),  -- 1000 watt supply AC
                                wscac1300(22),  -- 1300 watt supply AC
                                wscdc1000(23),  -- 1000 watt supply DC
                                wscdc1360(24),  -- 1360 watt supply DC
                                wsx4008(25),    -- 400 watt supply
                                wsc5518(26),    -- 805 watt supply AC
                                wsc5598(27),    -- 805 watt supply DC
                                w120(28),       -- 120 watt
                                externalPS(29), -- external power supply
                                wscac2500w(30), -- 2500 watt supply AC
                                wscdc2500w(31), -- 2500 watt supply DC
                                wsx4008dc(32),  -- 400 watt supply DC
                                wscac4000w(33), -- 4000 watt supply AC
                                pwr4000dc(34),  -- 4000 watt supply DC
                                pwr950ac(35),   -- 950 watt supply AC
                                pwr950dc(36),   -- 950 watt supply DC
                                pwr1900ac(37),  -- 1900 watt supply AC
                                pwr1900dc(38),  -- 1900 watt supply DC
                                pwr1900ac6(39), -- 1900 watt supply
                                                -- AC/6 slots
                                wsx4008ac650w(42), -- 650 watt supply AC
                                wsx4008dc650w(43), -- 650 watt supply DC
                                wscac3000w(44),   -- 3000 watt supply AC
                                pwrc451000ac(46), -- 1000 watt supply AC
                                pwrc452800acv(47),-- 2800 watt supply AC
                                pwrc451300acv(48),-- 1300 watt supply AC
                                pwrc451400dcp(49),-- 1400 watt supply DC
                                wscdc3000w(50),   -- 3000 watt supply DC
                                pwr1400ac(51),    -- 1400 watt supply AC
                                w156(52),         -- 156 watt supply AC
                                wscac6000w(53),   -- 6000 watt supply AC
                                pwr2700ac(54),    -- 2700 watt supply AC
                                pwr2700dc(55),    -- 2700 watt supply DC
                                wscac8700we(58),  -- 8700 watt supply AC
                                pwr2700ac4(59),   -- 2700 watt supply AC
                                pwr2700dc4(60),   -- 2700 watt supply DC
                                pwr400dc(63),     -- 400 watt supply DC
                                pwr400ac(64),     -- 400 watt supply AC
                                pwr6000dc(105),   -- 6000 watt supply DC
                                pwr1500dc(106)    -- 1500 watt supply DC
                                }
        MAX-ACCESS    read-only
        STATUS        current
        DESCRIPTION   "Type of power supply number 1."
        ::= { chassisGrp 3 }

chassisPs1Status OBJECT-TYPE
        SYNTAX        INTEGER {
                                other(1),       -- none of the following
                                ok(2),          -- status ok
                                minorFault(3),  -- minor problem
                                majorFault(4)   -- major problem
                                }
        MAX-ACCESS    read-only
        STATUS        current
        DESCRIPTION   "Status of power supply number 1. If the status is
                      not ok, the value of chassisPs1TestResult gives
                      more detailed information about the power supply's
                      failure condition(s)."
        ::= { chassisGrp 4 }

chassisPs1TestResult OBJECT-TYPE
        SYNTAX        INTEGER (0..65535)
        MAX-ACCESS    read-only
        STATUS        current
        DESCRIPTION   "Test result for power supply number 1. A zero
                      indicates that the supply passed all tests. Bits
                      set in the result indicate error conditions."
        ::= { chassisGrp 5 }

chassisPs2Type OBJECT-TYPE
        SYNTAX        INTEGER {
                                other(1),       -- none of the following
                                none(2),        -- no power supply
                                w50(3),         -- 50 watt supply
                                w200(4),        -- 200 watt supply
                                w600(5),        -- 600 watt supply
                                w80(6),         -- 80 watt supply
                                w130(7),        -- 130 watt supply
                                wsc5008(8),     -- 376 watt supply
                                wsc5008a(9),    -- 376 watt supply w/PFC
                                w175(10),       -- 175 watt supply
                                wsc5068(11),    -- 376 watt supply DC
                                wsc5508(12),    -- 1100 watt supply
                                wsc5568(13),    -- 1200 watt supply DC
                                wsc5508a(14),   -- 1200 watt supply
                                w155(15),       -- 155 watt supply
                                w175pfc(16),    -- 175 watt supply w/PFC
                                w175dc(17),     -- 175 watt supply DC
                                wsc5008b(18),   -- 376 watt supply
                                                -- w/PFC, OCP
                                wsc5008c(19),   -- 436 watt supply w/PFC
                                wsc5068b(20),   -- 376 watt supply DC
                                                -- w/OCP
                                wscac1000(21),  -- 1000 watt supply AC
                                wscac1300(22),  -- 1300 watt supply AC
                                wscdc1000(23),  -- 1000 watt supply DC
                                wscdc1360(24),  -- 1360 watt supply DC
                                wsx4008(25),    -- 400 watt supply
                                wsc5518(26),    -- 805 watt supply AC
                                wsc5598(27),    -- 805 watt supply DC
                                w120(28),       -- 120 watt
                                externalPS(29), -- external power supply
                                wscac2500w(30), -- 2500 watt supply AC
                                wscdc2500w(31), -- 2500 watt supply DC
                                wsx4008dc(32),  -- 400 watt supply DC
                                wscac4000w(33), -- 4000 watt supply AC
                                pwr4000dc(34),  -- 4000 watt supply DC
                                pwr950ac(35),   -- 950 watt supply AC
                                pwr950dc(36),   -- 950 watt supply DC
                                pwr1900ac(37),  -- 1900 watt supply AC
                                pwr1900dc(38),  -- 1900 watt supply DC
                                pwr1900ac6(39), -- 1900 watt supply
                                                -- AC/6 slots
                                wsx4008ac650w(42), -- 650 watt supply AC
                                wsx4008dc650w(43), -- 650 watt supply DC
                                wscac3000w(44),   -- 3000 watt supply AC
                                pwrc451000ac(46), -- 1000 watt supply AC
                                pwrc452800acv(47),-- 2800 watt supply AC
                                pwrc451300acv(48),-- 1300 watt supply AC
                                pwrc451400dcp(49),-- 1400 watt supply DC
                                wscdc3000w(50),   -- 3000 watt supply DC
                                pwr1400ac(51),    -- 1400 watt supply AC
                                w156(52),         -- 156 watt supply AC
                                wscac6000w(53),   -- 6000 watt supply AC
                                pwr2700ac(54),    -- 2700 watt supply AC
                                pwr2700dc(55),    -- 2700 watt supply DC
                                wscac8700we(58),  -- 8700 watt supply AC
                                pwr2700ac4(59),   -- 2700 watt supply AC
                                pwr2700dc4(60),   -- 2700 watt supply DC
                                pwr400dc(63),     -- 400 watt supply DC
                                pwr400ac(64),     -- 400 watt supply AC
                                pwr6000dc(105),   -- 6000 watt supply DC
                                pwr1500dc(106)    -- 1500 watt supply DC
                                }
        MAX-ACCESS    read-only
        STATUS        current
        DESCRIPTION   "Type of power supply number 2."
        ::= { chassisGrp 6 }

chassisPs2Status OBJECT-TYPE
        SYNTAX        INTEGER {
                                other(1),       -- none of the following
                                ok(2),          -- status ok
                                minorFault(3),  -- minor problem
                                majorFault(4)   -- major problem
                                }
        MAX-ACCESS    read-only
        STATUS        current
        DESCRIPTION   "Status of power supply number 2. If the status is
                      not ok, the value of chassisPs2TestResult gives
                      more detailed information about the power supply's
                      failure condition(s)."
        ::= { chassisGrp 7 }

chassisPs2TestResult OBJECT-TYPE
        SYNTAX        INTEGER (0..65535)
        MAX-ACCESS    read-only
        STATUS        current
        DESCRIPTION   "Test result for power supply number 2. A zero
                      indicates that the supply passed all tests. Bits
                      set in the result indicate error conditions."
        ::= { chassisGrp 8 }

chassisFanStatus OBJECT-TYPE
        SYNTAX        INTEGER {
                                other(1),       -- none of the following
                                ok(2),          -- status ok
                                minorFault(3),  -- minor problem
                                majorFault(4)   -- major problem
                                }
        MAX-ACCESS    read-only
        STATUS        current
        DESCRIPTION   "Status of the chassis fan. If the status is not
                      ok, the value of chassisFanTestResult gives more
                      detailed information about the fan's failure
                      condition(s)."
        ::= { chassisGrp 9 }

chassisFanTestResult OBJECT-TYPE
        SYNTAX        INTEGER (0..65535)
        MAX-ACCESS    read-only
        STATUS        current
        DESCRIPTION   "Test result for the chassis fan. A zero indicates
                      that the fan passed all tests. Bits set in the
                      result indicate error conditions."
        ::= { chassisGrp 10 }

chassisMinorAlarm OBJECT-TYPE
        SYNTAX        INTEGER {
                                off(1),
                                on(2)
                                }
        MAX-ACCESS    read-only
        STATUS        current
        DESCRIPTION   "The chassis minor alarm status."
        ::= { chassisGrp 11 }

chassisMajorAlarm OBJECT-TYPE
        SYNTAX        INTEGER {
                                off(1),
                                on(2)
                                }
        MAX-ACCESS    read-only
        STATUS        current
        DESCRIPTION   "The chassis major alarm status."
        ::= { chassisGrp 12 }

chassisTempAlarm OBJECT-TYPE
        SYNTAX        INTEGER {
                                off(1),     -- temperature within normal
                                            --  range
                                on(2),      -- temperature too high
                                critical(3) -- critical temperature,
                                            -- system shut down imminent
                                }
        MAX-ACCESS    read-only
        STATUS        current
        DESCRIPTION   "The chassis temperature alarm status."
        ::= { chassisGrp 13 }

chassisNumSlots OBJECT-TYPE
        SYNTAX        INTEGER (1..16)
        MAX-ACCESS    read-only
        STATUS        current
        DESCRIPTION   "The number of slots in the chassis available for
                      plug-in modules."
        ::= { chassisGrp 14 }

chassisSlotConfig OBJECT-TYPE
        SYNTAX        INTEGER (0..65535)
        MAX-ACCESS    read-only
        STATUS        current
        DESCRIPTION   "An indication of which slots in the chassis have
                      modules inserted. This is an integer value with
                      bits set to indicate configured modules. It can be
                      interpreted as a sum of f(x) as x goes from 1 to
                      the number of slots, where f(x) = 0 for no module
                      inserted and f(x) = exp(2, x-1) for a module
                      inserted."
        ::= { chassisGrp 15 }

chassisModel OBJECT-TYPE
        SYNTAX        DisplayString (SIZE (0..20))
        MAX-ACCESS    read-only
        STATUS        current
        DESCRIPTION   "The manufacturer's model number for the chassis."
        ::= { chassisGrp 16 }

chassisSerialNumber OBJECT-TYPE
        SYNTAX        INTEGER (0..999999999)
        MAX-ACCESS    read-only
        STATUS        deprecated
        DESCRIPTION   "The serial number of the chassis in a numeric
                      format. If the chassis uses an alphanumeric
                      serial number, this MIB object will return 0.

                      This object is deprecated and replaced by
                      entPhysicalSerialNum in ENTITY-MIB."
        ::= { chassisGrp 17 }

-- chassis component table

chassisComponentTable OBJECT-TYPE
        SYNTAX        SEQUENCE OF ChassisComponentEntry
        MAX-ACCESS    not-accessible
        STATUS        deprecated
        DESCRIPTION   "A list of the chassis related components in the
                      chassis.

                      This table is deprecated and replaced by
                      entPhysicalTable in ENTITY-MIB."
        ::= { chassisGrp 18 }

chassisComponentEntry OBJECT-TYPE
        SYNTAX        ChassisComponentEntry
        MAX-ACCESS    not-accessible
        STATUS        deprecated
        DESCRIPTION   "Entry containing information about one component
                      in the chassis."
        INDEX         { chassisComponentIndex }
        ::= { chassisComponentTable 1 }

ChassisComponentEntry ::=
        SEQUENCE {
                chassisComponentIndex
                        INTEGER,
                chassisComponentType
                        INTEGER,
                chassisComponentSerialNumber
                        DisplayString,
                chassisComponentHwVersion
                        DisplayString,
                chassisComponentModel
                        DisplayString
        }

chassisComponentIndex OBJECT-TYPE
        SYNTAX        INTEGER (1..65535)
        MAX-ACCESS    read-only
        STATUS        deprecated
        DESCRIPTION   "A unique value for each chassis related component
                      within the chassis."
        ::= { chassisComponentEntry 1 }

chassisComponentType OBJECT-TYPE
        SYNTAX        INTEGER {
                        unknown(1),      -- unknown chassis component
                        wsc6000cl(2),    -- clock module for cat6000
                        wsc6000vtt(3),   -- VTT module for cat6000
                        wsc6000tempSensor(4), -- Temp Sensor for cat6000
                        wsc6513Clock(5), -- clock for WS-C6513
                        clk7600(6),    -- clock module for cisco7600
                        ws9SlotFan(7), -- Catalyst 6000 Fan Tray for
                                       -- 9-Slot Systems
                        fanMod9(8),    -- Cisco 7609 and Catalyst
                                       -- 6509-NEB-A Fan Tray
                        wsc6506eFan(10), -- Catalyst 6506 E FAN Tray
                        wsc6509eFan(11), -- Catalyst 6509 E FAN Tray
                        wsc6503eFan(13), -- Catalyst 6503 E FAN Tray
                        wsc6000vtte(14), -- VTT module for cat6000 E
                        fanMod4Hs(15),   -- Fan module for cisco7604
                                         -- and WS-C6504
                        fan6524(16),     -- Catalyst 6524 Series FAN Tray
                        fanMod6Shs(17),  -- 6-slot FAN for CISCO7606-S
                        fanMod9Shs(18),  -- 9-slot FAN for CISCO7609-S
                        fanMod9St(19),   -- 9-slot FAN for CISCO7609-S
                        wsc6509veFan(20),-- Fan Tray for WS-C6509-V-E
                        fanMod3Hs(21)    -- Fan Tray for CISCO7603-S
                      }
        MAX-ACCESS    read-only
        STATUS        deprecated
        DESCRIPTION   "The type of the chassis component."
        ::= { chassisComponentEntry 2 }

chassisComponentSerialNumber OBJECT-TYPE
        SYNTAX        DisplayString (SIZE (0 .. 20))
        MAX-ACCESS    read-only
        STATUS        deprecated
        DESCRIPTION   "The serial number of the chassis component."
        ::= { chassisComponentEntry 3 }

chassisComponentHwVersion OBJECT-TYPE
        SYNTAX        DisplayString (SIZE (0 .. 20))
        MAX-ACCESS    read-only
        STATUS        deprecated
        DESCRIPTION   "The hardware version of the chassis component."
        ::= { chassisComponentEntry 4 }

chassisComponentModel OBJECT-TYPE
        SYNTAX        DisplayString (SIZE (0 .. 20))
        MAX-ACCESS    read-only
        STATUS        deprecated
        DESCRIPTION   "The manufacturer's model number for the chassis
                      component."
        ::= { chassisComponentEntry 5 }

chassisSerialNumberString OBJECT-TYPE
        SYNTAX        DisplayString (SIZE (0..20))
        MAX-ACCESS    read-only
        STATUS        current
        DESCRIPTION   "The serial number of the chassis. This MIB object
                      will return the chassis serial number for any
                      chassis that either a numeric or an alphanumeric
                      serial number is being used."
        ::= { chassisGrp 19 }

chassisPs3Type OBJECT-TYPE
        SYNTAX        INTEGER {
                                other(1),      -- none of the following
                                none(2),       -- no power supply
                                wsx4008(25),   -- 400 watt supply
                                wsx4008dc(32), -- 400 watt supply DC
                                wsx4008ac650w(42), -- 650 watt supply AC
                                wsx4008dc650w(43)  -- 650 watt supply DC
                              }
        MAX-ACCESS    read-only
        STATUS        current
        DESCRIPTION   "Type of power supply number 3. This object is
                      only supported by systems that can have 3 or more
                      power supplies."
        ::= { chassisGrp 20 }

chassisPs3Status OBJECT-TYPE
        SYNTAX        INTEGER {
                                other(1),      -- none of the following
                                ok(2),         -- status ok
                                minorFault(3), -- minor problem
                                majorFault(4)  -- major problem
                                }
        MAX-ACCESS    read-only
        STATUS        current
        DESCRIPTION   "Status of power supply number 3. If the status is
                      not ok, the value of chassisPs3TestResult gives
                      more detailed information about the power supply's
                      failure condition(s). This object is only
                      supported by systems that can have 3 or more
                      power supplies."
        ::= { chassisGrp 21 }

chassisPs3TestResult OBJECT-TYPE
        SYNTAX        INTEGER (0..65535)
        MAX-ACCESS    read-only
        STATUS        current
        DESCRIPTION   "Test result for power supply number 3. A zero
                      indicates that the supply passed all tests. Bits
                      set in the result indicate error conditions. This
                      object is only supported by systems that can
                      have 3 or more power supplies."
        ::= { chassisGrp 22 }

chassisPEMInstalled OBJECT-TYPE
        SYNTAX        TruthValue
        MAX-ACCESS    read-only
        STATUS        current
        DESCRIPTION   "Indicates whether Power Entry Module is installed
                      into the Chassis or not. Power Entry Module is a
                      connection into the system for an external
                      power supply of -48 Volts. This object is only
                      supported by systems that can have 3 or more power
                      supplies."
         ::= { chassisGrp 23 }



-- the module group

moduleTable OBJECT-TYPE
        SYNTAX        SEQUENCE OF ModuleEntry
        MAX-ACCESS    not-accessible
        STATUS        current
        DESCRIPTION   "A list of module entries. The number of entries
                      is the number of modules in the chassis."
        ::= { moduleGrp 1 }

moduleEntry OBJECT-TYPE
        SYNTAX        ModuleEntry
        MAX-ACCESS    not-accessible
        STATUS        current
        DESCRIPTION   "Entry containing information about one module in
                      the chassis."
        INDEX         { moduleIndex }
        ::= { moduleTable 1 }

ModuleEntry ::=
        SEQUENCE {
                moduleIndex
                        INTEGER,
                moduleType
                        INTEGER,
                moduleSerialNumber
                        INTEGER,
                moduleHwHiVersion
                        INTEGER,
                moduleHwLoVersion
                        INTEGER,
                moduleFwHiVersion
                        INTEGER,
                moduleFwLoVersion
                        INTEGER,
                moduleSwHiVersion
                        INTEGER,
                moduleSwLoVersion
                        INTEGER,
                moduleStatus
                        INTEGER,
                moduleTestResult
                        INTEGER,
                moduleAction
                        INTEGER,
                moduleName
                        DisplayString,
                moduleNumPorts
                        INTEGER,
                modulePortStatus
                        OCTET STRING,
                moduleSubType
                        INTEGER,
                moduleModel
                        DisplayString,
                moduleHwVersion
                        DisplayString,
                moduleFwVersion
                        DisplayString,
                moduleSwVersion
                        DisplayString,
                moduleStandbyStatus
                        INTEGER,
                moduleIPAddress
                        IpAddress,
                moduleIPAddressVlan
                        VlanIndex,
                moduleSubType2
                        INTEGER,
                moduleSlotNum
                        INTEGER,
                moduleSerialNumberString
                        DisplayString,
                moduleEntPhysicalIndex
                        PhysicalIndex,
                moduleAdditionalStatus
                        BITS
        }

moduleIndex OBJECT-TYPE
        SYNTAX        INTEGER (1..16)
        MAX-ACCESS    read-only
        STATUS        current
        DESCRIPTION   "A unique value for each module within the
                       chassis."
        ::= { moduleEntry 1 }

moduleType OBJECT-TYPE
        SYNTAX        INTEGER {
                other(1),    -- none of the following
                empty(2),    -- nothing installed
                wsc1000(3),  -- 2+8 Port CDDI Concentrator
                wsc1001(4),  -- 2+8 Port FDDI Concentrator
                wsc1100(5),  -- 2+16 Port FDDI/CDDI Concentrator
                wsc1200(11), -- 2+8 Port FDDI/Ethernet Switch
                wsc1400(12), -- 2 slot FDDI/CDDI Concentrator

                -- the following modules are for the WS-C1400
                wsx1441(13), -- 8 port Multi Mode FDDI (MIC connector)
                wsx1444(14), -- 8 port Single Mode FDDI (ST connector)
                wsx1450(15), -- 2 port MM FDDI (MIC), 12 port
                             -- CDDI(RJ-45)
                wsx1483(16), -- 16 port CDDI (RJ-45 connector)
                wsx1454(17), -- 2 port SM FDDI (ST), 12 port CDDI
                             -- (RJ-45)
                wsx1455(18), -- 10 port MM FDDI (SC connector)
                wsx1431(19), -- 4 port Multi Mode FDDI (MIC connector)
                wsx1465(20), -- 2 port MM FDDI (SC), 12 port CDDI
                             -- (RJ-45)
                wsx1436(21), -- 4 port SM FDDI (ST), 4 port MM FDDI
                             -- (MIC)
                wsx1434(22), -- 4 port Single Mode FDDI (ST connector)

                -- the following modules are for the WSC-5000 series
                wsx5009(23), -- Supervisor Module 1, 2 100 BaseTX
                             -- (RJ-45/MII)
                wsx5013(24), -- 24 port 10BaseT (RJ-45 connector)
                wsx5011(25), -- 12 port 10BaseFL MultiMode (ST
                             -- connector)
                wsx5010(26), -- 24 port 10BaseT (Telco connector)
                wsx5113(27), -- 12 port 100BaseTX (RJ-45 connector)
                wsx5101(28), -- 1 dual attach Multi Mode FDDI
                             -- (MIC connector)
                wsx5103(29), -- 1 dual attach CDDI (RJ-45 connector)
                wsx5104(30), -- 1 dual attach Single Mode FDDI (ST
                             -- connector)
                wsx5155(32), -- 1 port Multi Mode OC-3 ATM (SC
                             -- connector)
                wsx5154(33), -- 1 port Single Mode OC-3 ATM (SC
                             -- connector)
                wsx5153(34), -- 1 port UTP OC-3 ATM (RJ-45 connector)
                wsx5111(35), -- 12 port 100BaseFX Multi Mode (SC
                             -- connector)
                wsx5213(36), -- 12 port 10/100BaseTX (RJ-45 connector)
                wsx5020(37), -- 48 port 4 segment 10BaseT (Telco
                             -- connector)
                wsx5006(38), -- Supervisor Mod 1, 2 100BaseFX Multi Mode
                             -- (SC)
                wsx5005(39), -- Supervisor Mod 1, 2 100BaseFX Single
                             -- Mode (SC)
                wsx5509(40), -- Supervisor Mod 2, 2 100BaseTX
                             -- (RJ-45/MII)
                wsx5506(41), -- Supervisor Mod 2, 2 100BaseFX Multi Mode
                             -- (SC)
                wsx5505(42), -- Supervisor Mod 2, 2 100BaseFX Single
                             -- Mode (SC)
                wsx5156(43), -- 1 dual phy UTP OC-3 ATM (RJ-45
                             -- connector)
                wsx5157(44), -- 1 dual phy Single Mode OC-3 ATM (SC
                             -- connector)
                wsx5158(45), -- 1 dual phy Multi Mode OC-3 ATM (SC
                             -- connector)
                wsx5030(46), -- 16 port Token Ring (RJ-45 connector)
                wsx5114(47), -- 6 port SM, 6 port MM 100BaseFX (SC
                             -- connector)
                wsx5223(48), -- 24 port 3 segment 100BaseTX (RJ-45
                             -- connector)
                wsx5224(49), -- 24 port 10/100BaseTX (RJ-45 connector)
                wsx5012(50), -- 48 port 10BaseT (Telco connector)
                wsx5302(52), -- Vlan router
                wsx5213a(53), -- 12 port 10/100BaseTX (RJ-45 connector)
                wsx5380(54), -- Network Analysis Module
                wsx5201(55), -- 12 port 100BaseFX Multi Mode (SC
                             -- connector)
                wsx5203(56), -- 12 port 10/100BaseTX (RJ-45 connector)
                wsx5530(57), -- Supervisor Module 3
                wsx5161(61), -- 1 dual phy Multi Mode OC-12 ATM (SC
                             -- connector)
                wsx5162(62), -- 1 dual phy Single Mode OC-12 ATM (SC
                             -- connector)
                wsx5165(65), -- ATM bridge
                wsx5166(66), -- 1 dual phy DS3 ATM (BNC connector)
                wsx5031(67), -- 16 port Multi Mode Token Ring (ST
                             -- connector)
                wsx5410(68), -- 9 port 1000BaseX (GBIC connector)
                wsx5403(69), -- 3 port 1000BaseX (GBIC connector)
                wsx5201r(73), -- 12 port 100BaseFX Multi Mode (SC
                              --connector)
                wsx5225r(74), -- 24 port 10/100BaseTX (RJ-45 connector)
                wsx5014(75), -- 48 port 10BaseT (RJ-45 connector)
                wsx5015(76), -- 24 port 10BaseFL (MT-RJ connector)
                wsx5236(77), -- 24 port 100BaseFX Multi Mode (MT-RJ
                             -- connector)
                wsx5540(78), -- Supervisor Module 2 GS
                wsx5234(79), -- 24 port 10/100BaseTX (RJ-45 connector)
                wsx5012a(81), -- 48 port 10BaseT (Telco connector)
                wsx5167(82), -- 1 dual phy Multi Mode OC-3 ATM (SC
                             -- connector)
                wsx5239(83), -- 36 port 10/100BaseTX (Telco connector)
                wsx5168(84), -- 1 dual phy Single Mode OC-3 ATM (SC
                             -- connector)
                wsx5305(85), -- 8 port 100BaseFX MM (SC)/Ethernet bridge
                wsx5550(87), -- Supervisor Module 3 GS, 2 port GBIC
                wsf5541(88), -- RSFC for wsx5540, wsx5550
                wsx5534(91), -- Supervisor Module 3 FSX
                wsx5536(92), -- Supervisor Module 3 FLX
                wsx5237(96), -- 24 port 100BaseFX Single Mode (MT-RJ
                             -- connector)

                -- the following modules are for the WSC-6000 series
                wsx6ksup12ge(200), -- 2 port 1000BaseX Supervisor Mod
                                   -- (GBIC)
                wsx6408gbic(201),  -- 8 port 1000BaseX (GBIC)
                wsx6224mmmt(202),  -- 24 port 100BaseFX MM (MT-RJ)
                wsx6248rj45(203),  -- 48 port 10/100BaseTX (RJ-45)
                wsx6248tel(204),   -- 48 port 10/100BaseTX (Telco)
                wsx6302msm(206),   -- Multilayer switch module
                wsf6kmsfc(207),    -- Multilayer switch feature card
                wsx6024flmt(208),  -- 24 port 10BaseFL (MT-RJ)
                wsx6101oc12mmf(209),-- 1 port Multi Mode OC-12 ATM (SC)
                wsx6101oc12smf(210),-- 1 port Single Mode OC-12 ATM (SC)
                wsx6416gemt(211),  -- 16 port 1000BaseSX (MT-RJ)
                wsx61822pa(212),   -- 2 port adapter FlexWAN Module
                osm2oc12AtmMM(213),-- 2-port OC-12 ATM MM
                osm2oc12AtmSI(214),-- 2-port OC-12 ATM SI
                osm4oc12PosMM(216),-- 4-port OC-12c POS MM
                osm4oc12PosSI(217),-- 4-port OC-12c POS SI
                osm4oc12PosSL(218),-- 4-port OC-12c POS SL
                wsx6ksup1a2ge(219),-- 2 port 1000BaseX Supervisor Mod
                                   -- (GBIC)
                wsx6302amsm(220),  -- Multilayer switch module (Rev. A)
                wsx6416gbic(221),  -- 16 port 1000BaseX (GBIC)
                wsx6224ammmt(222), -- 24 port 100BaseFX MM (MT-RJ),
                                   -- Enhanced QoS
                wsx6380nam(223),   -- Network Analysis Module
                wsx6248arj45(224), -- 48 port 10/100BaseTX (RJ-45)
                                   -- Enhanced QoS
                wsx6248atel(225),  -- 48 port 10/100BaseTX (Telco)
                                   -- Enhanced QoS
                wsx6408agbic(226), -- 8 port 1000BaseX (GBIC),Enhanced
                                   -- QoS
                wsx6608t1(229),    -- 8 port T1 (1.544 Mps)
                wsx6608e1(230),    -- 8 port E1 (2.048 Mps)
                wsx6624fxs(231),   -- 24 port FXS Analog station module
                wsx6316getx(233),  -- 16 port 1000BaseT (RJ-45)
                wsf6kmsfc2(234),   -- Multilayer switch feature card II
                wsx6324mmmt(235),  -- 24 port 100BaseFX MM (MT-RJ)
                wsx6348rj45(236),  -- 48 port 10/100BaseTX (RJ-45)
                wsx6ksup22ge(237), -- 2 port 1000BaseX Supervisor Mod 2
                                   -- (GBIC)
                wsx6324sm(238),    -- 24 port 100BaseFX SM (MT-RJ)
                wsx6516gbic(239),  -- 16 port 1000BaseX (GBIC)
                osm4geWanGbic(240), -- 4 port 1000BaseX (GBIC)
                osm1oc48PosSS(241), -- 1 port OC-48 POS SS
                osm1oc48PosSI(242), -- 1 port OC-48 POS SI
                osm1oc48PosSL(243), -- 1 port OC-48 POS SL
                wsx6381ids(244),    -- Intrusion Detection module
                wsc6500sfm(245),    -- Switch Fabric Module
                osm16oc3PosMM(246), -- 16 port OC3 POS MM
                osm16oc3PosSI(247), -- 16 port OC3 POS SI
                osm16oc3PosSL(248), -- 16 port OC3 POS SL
                osm2oc12PosMM(249), -- 2 port OC12 POS MM
                osm2oc12PosSI(250), -- 2 port OC12 POS SI
                osm2oc12PosSL(251), -- 2 port OC12 POS SL
                wsx650210ge(252),   -- 1 port 10 Gigabit Ethernet
                osm8oc3PosMM(253),  -- 8 port OC3 POS MM
                osm8oc3PosSI(254),  -- 8 port OC3 POS SI
                osm8oc3PosSL(255),  -- 8 port OC3 POS SL
                wsx6548rj45(258),   -- 48 port 10/100BaseTX (RJ-45)
                wsx6524mmmt(259),   -- 24 port 100BaseFX MM (MT-RJ)
                wsx6066SlbApc(260), -- SLB Application Processor Complex
                wsx6516getx(261),   -- 16 port 10/100/1000BaseT (RJ-45)
                osm2oc48OneDptSS(265), -- 2 port OC48 1 DPT SS
                osm2oc48OneDptSI(266), -- 2 port OC48 1 DPT SI
                osm2oc48OneDptSL(267), -- 2 port OC48 1 DPT SL
                osm2oc48OneDptSSDual(268),  -- 2 port OC48 DPT SS
                                            --   dual-natured
                osm2oc48OneDptSIDual(269),  -- 2 port OC48 DPT SI
                                            --   dual-natured
                osm2oc48OneDptSLDual(270),  -- 2 port OC48 DPT SL
                                            --   dual-natured
                wsx6816gbic(271),    -- 16 port 1000BaseX (Layer 3)
                osm4choc12T3MM(272), -- 4 port OC-12 Multimode
                osm4choc12T3SI(273), -- 4 port OC-12 Singlemode
                                     -- Intermediate
                osm8choc12T3MM(274), -- 8 port OC-12 Multimode
                osm8choc12T3SI(275), -- 8 port OC-12 Singlemode
                                     -- Intermediate
                osm1choc48T3SS(276), -- 1 port OC-48 Singlemode Short
                osm2choc48T3SS(277), -- 2 port OC-48 Singlemode Short
                wsx6500sfm2(278),    -- Switch Fabric Module 136
                osm1choc48T3SI(279), -- 1 port OC-48 Singlemode
                                     -- Intermediate
                osm2choc48T3SI(280), -- 2 port OC-48 Singlemode
                                     -- Intermediate
                wsx6348rj21(281),    -- 48 port 10/100BaseTX (RJ-21)
                wsx6548rj21(282),    -- 48 port 10/100BaseTX (RJ-21)
                wsSvcCmm(284),       -- AVVID Services Module
                wsx650110gex4(285),  -- 1 port 10 Gigabit Ethernet (EX4)
                osm4oc3PosSI(286),   -- 4 port OC3 POS SI
                osm4oc3PosMM(289),   -- 4 port OC3 POS MM
                wsSvcIdsm2(290),     -- Intrusion Detection module
                wsSvcNam2(291),      -- Network Analysis Module
                wsSvcFwm1(292),      -- Firewall Module
                wsSvcCe1(293),       -- Web Cache/Content Engine Module
                wsSvcSsl1(294),      -- SSL Module
                osm8choc3DS0SI(295), -- 8 port OC3 DS0 SI
                osm4choc3DS0SI(296), -- 4 port OC3 DS0 SI
                osm1choc12T1SI(297), -- 1 port OC3 T1 SI

                -- the following modules are for the WSC-4000 series
                wsx4012(300),      -- Supervisor Module
                wsx4148rj(301),    -- 48 port 10/100BaseTX (RJ-45)
                wsx4232gbrj(302),  -- 2 1000X (GBIC), 32 10/100BaseTX
                                   -- (RJ-45)
                wsx4306gb(303),    -- 6 port 1000BaseX (GBIC)
                wsx4418gb(304),    -- 18 port 1000BaseX (GBIC)
                wsx44162gbtx(305), -- 2 1000BaseX (GBIC), 16 1000BaseT
                                   -- (RJ-45)
                wsx4912gb(306),    -- 12 port 1000BaseX (GBIC)
                wsx2948gbrj(307),  -- 2 1000X (GBIC), 48 10/100BaseTX
                                   -- (RJ-45)
                wsx2948(309),      -- Supervisor Module
                wsx4912(310),      -- Supervisor Module
                wsx4424sxmt(311),  -- 24 port 1000BaseSX (MT-RJ)
                wsx4232rjxx(312),  -- 32 port 10/100 (RJ-45) + uplink
                                   -- submodule
                wsx4148rj21(313),  -- 48 port 10/100BaseTX (RJ-21)
                wsx4124fxmt(317),  -- 24 port 100BaseFX MM (MT-RJ)
                wsx4013(318),      -- Supervisor Module 2, 2 port
                                   -- 1000X(GBIC)
                wsx4232l3(319),    -- 32 10/100TX(RJ-45), 2 1000X
                                   -- Routed port
                wsx4604gwy(320),   -- 1 port 1000 Mb routed + 1 daughter
                                   -- card
                wsx44122Gbtx(321), -- 2 1000BaseX(GBIC), 12 1000BaseT
                                   -- (RJ-45)
                wsx2980(322),      -- Supervisor module for wsc2980g
                wsx2980rj(323),    -- 48 port 10/100BaseTX
                wsx2980gbrj(324),  -- 32 port 10/100BaseTX + 2 port
                                   -- 1000X
                wsx4019(325),      -- Switch Fabric Module
                wsx4148rj45v(326), -- 48 port 10/100BaseT Voice Power
                                   -- module
                wsx4424gbrj45(330),-- 24 10/100/1000BaseTX (RJ-45)
                wsx4148fxmt(331),  -- 48 port 100BaseFX MM (MT-RJ)
                wsx4448gblx(332),  -- 48 port 1000BaseX (SFP GBIC)
                wsx4448gbrj45(334),  -- 48 port 10/100/1000Base TX
                                     -- (RJ-45)
                wsx4148lxmt(337),    -- 48 port 100BaseLX
                wsx4548gbrj45(339),  -- 48 port 10/100/1000Base TX
                                     -- (RJ-45)
                wsx4548gbrj45v(340), -- 48 port 10/100/1000T Voice
                                     -- module
                wsx4248rj21v(341),   -- 48 port 10/100 (RJ-21) Voice
                                     -- module
                wsx4302gb(342),      -- 2 port 1000BaseX (GBIC)
                wsx4248rj45v(343),   -- 48 port 10/100BaseT Voice Power
                                     -- module
                wsx2948ggetx(345),   -- Supervisor Module for
                                     -- wsc2948ggetx
                wsx2948ggetxgbrj(346), -- 4 1000Base FX(SFP), 48
                                       -- 10/100/1000 BaseTX (RJ-45)
                -- the following modules are for the WSC-6000 series
                wsx6516aGbic(502),   -- 16 port 1000BaseX (GBIC)
                wsx6148getx(503),    -- 48 port 10/100/1000BaseT(RJ-45)
                wsx6148x2rj45(506),  -- 96 port 10/100BaseTX (RJ-45)
                wsx6196rj21(507),    -- 96 port 10/100BaseTX (RJ-21)
                wssup32ge3b(509),    -- 8 port 1000BaseX Supervisor
                                     -- module
                wssup3210ge3b(510),  -- 2 port 10GBaseX Supervisor
                                     -- module
                mec6524gs8s(511),    -- 24 port SFP with 8 SFP uplinks
                mec6524gt8s(512),    -- 24 port 10/100/1000BaseT with
                                     -- 8 SFP uplinks
                wssup32pge(515),     -- 8 port 1000BaseX Supervisor
                                     -- module PISA
                wssup32p10ge(516),   -- 2 port 10GBaseX Supervisor
                                     -- module PISA
                wssvcpisa32(597),    -- PISA card (Multilayer switch &
                                     -- service feature card)
                                     -- (moduleSubType2)
                me6524msfc2a(598),   -- Multilayer switch feature card
                                     -- II A
                wsf6kmsfc2a(599),    -- Multilayer switch feature card
                                     -- II A

                -- WAN module for c6k and 76xx
                osm12ct3T1(600),     -- 12 port CT3 T1
                osm12t3e3(601),      -- 12 port T3 E3
                osm24t3e3(602),      -- 24 port T3 E3
                osm4GeWanGbicPlus(603), -- 4 GE WAN ports and 2 GE LAN ports
                osm1choc12T3SI(604), -- 1 port OC-12 Singlemode
                                     -- Intermediate
                osm2choc12T3SI(605), -- 2 port OC-12 Singlemode
                                     -- Intermediate
                osm2oc12AtmMMPlus(606), -- 2-port OC-12 ATM MM
                osm2oc12AtmSIPlus(607), -- 2-port OC-12 ATM SI
                osm2oc12PosMMPlus(608), -- 2 port OC12 POS MM
                osm2oc12PosSIPlus(609), -- 2 port OC12 POS SI
                osm16oc3PosSIPlus(610), -- 16 port OC3 POS SI
                osm1oc48PosSSPlus(611), -- 1 port OC-48 POS SS
                osm1oc48PosSIPlus(612), -- 1 port OC-48 POS SI
                osm1oc48PosSLPlus(613), -- 1 port OC-48 POS SL
                osm4oc3PosSIPlus(614),  -- 4 port OC3 POS SI
                osm8oc3PosSLPlus(615),  -- 8 port OC3 POS SL
                osm8oc3PosSIPlus(616),  -- 8 port OC3 POS SI
                osm4oc12PosSIPlus(617), -- 4 port OC12 POS SI

                wsSvcIpSec1(903),    -- VPN security blade module
                wsSvcMwam1(910),     -- Mobile Wireless Application
                                     -- Module
                wsSvcCsg1(911),      -- Content Services Gateway Module
                wsx6148rj45v(912),   -- 48 port 10/100BaseTX (RJ-45)
                wsx6148rj21v(913),   -- 48 port 10/100BaseTX (RJ-21)
                wsSvcNam1(914),      -- Network Analysis Module
                wsx6548getx(915),    -- 48 port 10/100/1000BaseT(RJ-45)
                wsSvcPsd1(919),      -- Persistent Store Device
                wsx6066SlbSk9(920),  -- Content Switching Module with
                                     -- SSL daughter card
                wsx6148agetx(921),   -- 48 port
                                     -- 10/100/1000BaseTX (RJ-45)
                wsx6148arj45(923),   -- 48 port 10/100BaseTX (RJ-45)
                wsSvcWlan1k9(924),   -- Wireless LAN Application Module
                wsSvcAon1k9(925),    -- Application Oriented Network
                                     -- Switching
                ace106500k9(926),    -- Application Control Engine
                                     -- 10G Service Module
                wsSvcWebVpnk9(927),  -- Web VPN Module
                wsx6148FeSfp(928),   -- 48 port 100Base-X SFP Module
                wsSvcAdm1k9(929),    -- Anomaly Detection Module
                wsSvcAgm1k9(930),    -- Anomaly Guard Module
                ace046500k9(936),    -- Application Control Engine
                                     -- 4G Service Module
                wsSvcSamiBb(940),    -- Service and Application Module
                                     -- for IP
                wssup720(1001),      -- Supervisor Mod 720 CPU board
                                     -- (moduleSubType2)
                wssup720base(1002),  -- Supervisor Mod 720 base board
                m7600Sip600(1004),   -- SPA (Shared Port Adapter)
                                     -- carrier card (SIP-10G)
                wsx6748getx(1007),   -- 48 port 10/100/1000 (RJ-45)
                wsx670410ge(1008),   -- 4 port 10 GE
                wsx6748sfp(1009),    -- 48 port 1000Base FX (SFP GBIC)
                wsx6724sfp(1010),    -- 24 port 1000Base FX (SFP GBIC)
                wsx670810ge(1016),   -- 8 port X2 10 GE with DFC
                vss72010g(1021),     -- Supervisor Mod 720 10G
                wsx671610ge(1027),   -- 16 port 10 GE

                -- constellation 2 WAN module
                wsx65822pa(1101),    -- Enhanced FlexWAN Module
                m7600Sip200(1102),   -- SPA (Shared Port Adapter)
                                     -- carrier card (SIP-1)
                m7600Sip400(1103),   -- SPA (Shared Port Adapter)
                                     -- carrier card (SIP-2)
                c7600ssc400(1104),   -- SPA Jacket card
                c7600ssc600(1105),   -- IPSEC-VPN SPA jacket card
                esm2x10ge(1106),     -- 2x10G CWAN

                -- 7600 only module
                rsp720(1800),        -- MSFC3 Daughterboard
                                     -- (moduleSubType2)
                rsp720base(1801),    -- Router Switch Processor 720
                                     -- (moduleSubType2)
                c7600msfc4(1805)     -- 7600 MSFC4 cpu daughtercard
                                     -- (moduleSubType2)
                }
        MAX-ACCESS    read-only
        STATUS        current
        DESCRIPTION   "The type of module."
        ::= { moduleEntry 2 }

moduleSerialNumber OBJECT-TYPE
        SYNTAX        INTEGER (0..999999999)
        MAX-ACCESS    read-only
        STATUS        deprecated
        DESCRIPTION   "The serial number of the module in a numeric
                      format. If the module uses an alphanumeric serial
                      number, this MIB object will return 0.

                      This object is deprecated and replaced by
                      entPhysicalSerialNum in ENTITY-MIB."
        ::= { moduleEntry 3 }

moduleHwHiVersion OBJECT-TYPE
        SYNTAX        INTEGER (0..65535)
        MAX-ACCESS    read-only
        STATUS        deprecated
        DESCRIPTION   "The high part of the hardware version of the
                      module.
                      For example, if the hardware version is 3.1, the
                      value of moduleHwHiVersion is 3.

                      This object is deprecated and replaced by
                      entPhysicalHardwareRev in ENTITY-MIB."
        ::= { moduleEntry 4 }

moduleHwLoVersion OBJECT-TYPE
        SYNTAX        INTEGER (0..65535)
        MAX-ACCESS    read-only
        STATUS        deprecated
        DESCRIPTION   "The low part of the hardware version of the
                      module.
                      For example, if the hardware version is 3.1, the
                      value of moduleHwLoVersion is 1.

                      This object is deprecated and replaced by
                      entPhysicalHardwareRev in ENTITY-MIB."
        ::= { moduleEntry 5 }

moduleFwHiVersion OBJECT-TYPE
        SYNTAX        INTEGER (0..65535)
        MAX-ACCESS    read-only
        STATUS        deprecated
        DESCRIPTION   "The high part of the firmware version number. For
                      example, if the firmware version is 3.1, the value
                      of moduleFwHiVersion is 3.

                      This object is deprecated and replaced by
                      entPhysicalFirmwareRev in ENTITY-MIB."
        ::= { moduleEntry 6 }

moduleFwLoVersion OBJECT-TYPE
        SYNTAX        INTEGER (0..65535)
        MAX-ACCESS    read-only
        STATUS        deprecated
        DESCRIPTION   "The low part of the firmware version number. For
                      example, if the firmware version is 3.1, the value
                      of moduleFwLoVersion is 1.

                      This object is deprecated and replaced by
                      entPhysicalFirmwareRev in ENTITY-MIB."
        ::= { moduleEntry 7 }

moduleSwHiVersion OBJECT-TYPE
        SYNTAX        INTEGER (0..65535)
        MAX-ACCESS    read-only
        STATUS        deprecated
        DESCRIPTION   "The high part of the software version number. For
                      example, if the software version is 3.1, the value
                      of moduleSwHiVersion is 3.

                      This object is deprecated and replaced by
                      entPhysicalSoftwareRev in ENTITY-MIB."
        ::= { moduleEntry 8 }

moduleSwLoVersion OBJECT-TYPE
        SYNTAX        INTEGER (0..65535)
        MAX-ACCESS    read-only
        STATUS        deprecated
        DESCRIPTION   "The low part of the software version number. For
                      example, if the software version is 3.1, the value
                      of moduleSwLoVersion is 1.

                      This object is deprecated and replaced by
                      entPhysicalSoftwareRev in ENTITY-MIB."
        ::= { moduleEntry 9 }

moduleStatus OBJECT-TYPE
        SYNTAX        INTEGER {
                                other(1),       -- none of the following
                                ok(2),          -- status ok
                                minorFault(3),  -- minor problem
                                majorFault(4)   -- major problem
                                }
        MAX-ACCESS    read-only
        STATUS        current
        DESCRIPTION   "The operational status of the module. If the
                      status is not ok, the value of moduleTestResult
                      gives more detailed information about the
                      module's failure condition(s)."
        ::= { moduleEntry 10 }

moduleTestResult OBJECT-TYPE
        SYNTAX        INTEGER (0..65535)
        MAX-ACCESS    read-only
        STATUS        current
        DESCRIPTION   "The result of the module's self test. A zero
                      indicates that the module passed all tests. Bits
                      set in the result indicate error conditions."
        ::= { moduleEntry 11 }

moduleAction OBJECT-TYPE
        SYNTAX        INTEGER {
                                other(1),
                                reset(2),
                                enable(3),
                                disable(4)
                                }
        MAX-ACCESS    read-write
        STATUS        current
        DESCRIPTION   "This object, when read, returns one of the
                      following results:
                          other(1):   module permanently enabled
                          enable(3):  module currently enabled
                          disable(4): module currently disabled
                      Setting this object to one of the acceptable
                      values gives the following results:
                        other(1):  gives an error
                        reset(2):  resets the module's control logic
                        enable(3): if the module status is configurable,
                                    enables the module, else gives error
                        disable(4): if the module status is
                                   configurable, disables the module,
                                   else gives error.
                      Setting this object to any other values results in
                      an error."
        ::= { moduleEntry 12 }

moduleName OBJECT-TYPE
        SYNTAX        DisplayString (SIZE (0..20))
        MAX-ACCESS    read-write
        STATUS        current
        DESCRIPTION   "A descriptive string used by the network
                      administrator to name the module."
        ::= { moduleEntry 13 }

moduleNumPorts OBJECT-TYPE
        SYNTAX        INTEGER (0..255)
        MAX-ACCESS    read-only
        STATUS        current
        DESCRIPTION   "The number of ports supported by the module."
        ::= { moduleEntry 14 }

modulePortStatus OBJECT-TYPE
        SYNTAX        OCTET STRING
        MAX-ACCESS    read-only
        STATUS        current
        DESCRIPTION   "A series of bytes containing status information
                      about the module and each of the ports on the
                      module.
                      The first byte contains the status for the module
                      (same value as moduleStatus), and subsequent bytes
                      contain status for the first through the last
                      ports on the module (same value as
                      portOperStatus)."
        ::= { moduleEntry 15 }

moduleSubType OBJECT-TYPE
        SYNTAX        INTEGER {
                                other(1),    -- none of the following
                                empty(2),    -- nothing installed

                               -- sub modules for the WS-X5505,5506,5509
                                wsf5510(3),  -- EARL 1
                                wsf5511(4),  -- EARL 1+

                                -- sub modules for the WS-X5302
                                wsx5304(6),  -- VIP II carrier

                                -- sub modules for the WS-X5530,5540
                                wsf5520(7),  -- EARL 1+
                                wsf5521(8),  -- NFFC
                                wsf5531(9),  -- NFFC II

                                -- sub modules for the WS-X6K-SUP-2GE
                                wsf6020(100), -- L2 switching card
                                wsf6020a(101),-- L2 switching card II
                                wsf6kpfc(102),-- L3 switching engine
                                wsf6kpfc2(103),-- L3 switching engine II

                                wsf6kvpwr(104), -- inline power card

                                wsf6kdfc(105),  -- distributed switching
                                                --  engine
                                wsf6kpfc2a(106),-- L3 switching engine
                                                -- IIA
                                wsf6kdfca(107), -- distributed switching
                                                -- engine

                                -- sub module for SPA Carrier Basecard
                                vsp300dfc(200),  -- VSP 300 Earl7
                                                 -- Daughtercard
                                wsf6kpfc3a(201),
                                       -- Policy feature card 3A
                                wsf6kdfc3a(202),
                                       -- Distributed forwarding card 3A
                                wsf6700dfc3a(203),
                                       -- Distributed forwarding card 3A
                                wsf6kdfc3bxl(205),
                                       -- Distributed forwarding card 3B
                                       -- XL
                                wsf6kpfc3bxl(206),
                                       -- Policy feature card 3B XL
                                wsf6700dfc3bxl(207),
                                       -- Distributed forwarding card 3B
                                       -- XL
                                wsf6700cfc(208),
                                       -- Centralized forwarding card
                                m7600pfc3c(213),
                                       -- Policy feature card 3C
                                wsf6kpfc3b(216),
                                       -- Policy feature card 3B
                                wsf6700dfc3b(217),
                                       -- Distributed forwarding card 3B
                                wsf6700dfc3c(218),
                                       -- Distributed forwarding card
                                wsf6700dfc3cxl(221),
                                       -- Distributed forwarding card
                                wsf6kdfc3b(223),
                                       -- Distributed forwarding card 3B
                                mec6524pfc3c(224),
                                       -- Policy feature card 3C
                                sip600earl(225),
                                       -- Distributed feature card
                                vsf6kpfc3cxl(226),
                                       -- Policy feature card 3C XL
                                vsf6kpfc3c(227),
                                       -- Policy feature card 3C
                                c7600esmdfc3cxl(228),
                                       -- Distributed forwarding card
                                       -- 3C XL
                                c7600esmdfc3c(230)
                                       -- Distributed forwarding card 3C
                                }
        MAX-ACCESS    read-only
        STATUS        current
        DESCRIPTION   "The type of daughterboard attached to this
                      module."
        ::= { moduleEntry 16 }

moduleModel OBJECT-TYPE
        SYNTAX        DisplayString (SIZE (0..20))
        MAX-ACCESS    read-only
        STATUS        current
        DESCRIPTION   "The manufacturer's model number for the module."
        ::= { moduleEntry 17 }

moduleHwVersion OBJECT-TYPE
        SYNTAX        DisplayString (SIZE (0..12))
        MAX-ACCESS    read-only
        STATUS        current
        DESCRIPTION   "The hardware version of the module."
        ::= { moduleEntry 18 }

moduleFwVersion OBJECT-TYPE
        SYNTAX        DisplayString (SIZE (0..40))
        MAX-ACCESS    read-only
        STATUS        current
        DESCRIPTION   "The firmware version of the module."
        ::= { moduleEntry 19 }

moduleSwVersion OBJECT-TYPE
        SYNTAX        DisplayString (SIZE (0..40))
        MAX-ACCESS    read-only
        STATUS        current
        DESCRIPTION   "The software version of the module."
        ::= { moduleEntry 20 }

moduleStandbyStatus OBJECT-TYPE
        SYNTAX        INTEGER {
                                other(1),       -- none of the following
                                active(2),
                                standby(3),
                                error(4)
                                }
        MAX-ACCESS    read-only
        STATUS        current
        DESCRIPTION   "Redundant status of a module that supports
                      redundancy."
        ::= { moduleEntry 21 }

moduleIPAddress OBJECT-TYPE
        SYNTAX        IpAddress
        MAX-ACCESS    read-only
        STATUS        current
        DESCRIPTION   "If the module has a separate IP address to
                       reach it by, then it is reported here.
                       Otherwise, this object has a value of
                       '00000000H'."
        ::= { moduleEntry 22 }

moduleIPAddressVlan OBJECT-TYPE
        SYNTAX        VlanIndex
        MAX-ACCESS    read-only
        STATUS        current
        DESCRIPTION   "If the moduleIPAddress is valid then this
                      object reports the VLAN to access that IP
                      address on. Otherwise this object has a value
                      of zero."
        ::= { moduleEntry 23 }

moduleSubType2 OBJECT-TYPE
        SYNTAX        INTEGER {
                other(1),    -- none of the following
                empty(2),    -- nothing installed

                -- sub module 2 type for the WS-X5530,5540
                wsu5531(3),  -- 2 port 10/100BaseTX (RJ-45)
                wsu5533(5),  -- 2 port 100BaseFX MM (SC)
                wsu5534(6),  -- 2 port 1000BaseSX (SC)
                wsu5535(7),  -- 2 port 100BaseFX SM (SC)
                wsu5536(8),  -- 2 port 1000BaseLX (SC)
                wsu5537(9),  -- 4 port 10/100BaseTX (RJ-45)
                wsu5538(10), -- 4 port 100BaseFX MM (SC)
                wsu5539(11), -- 4 port 100BaseFX SM (SC)

                -- sub module 2 type for WS-X6502-10GE
                -- The following two boards were cancelled
                wsg6488(102),  -- 10GE-LR  Serial 1310nm long haul
                wsg6489(103),  -- 10GE-SX4 850nm WWDM short reach
                wsg6483(104),  -- 10GE-ER  Serial 1550nm extended reach
                wsg6485(105),  -- 10GE-LX4 Campus 1310nm WWDM long
                               -- haul/short reach.

                wsf6kFe48af(106),   -- inline power card
                wsf6kGe48af(107),   -- inline power card
                wsf6kVpwrGe(108),   -- inline power card
                wsf6kFe48x2af(109), -- inline power card

                -- sub module 2 type for cat6k IOS Software
                wsf6kmsfc(207),  -- Multilayer switch feature card
                wsf6kmsfc2(234), -- Multilayer switch feature card II

                -- sub module 2 type for WS-X4232,4224,4416
                wsu4504fxmt(314), -- 4 port 100BaseFX (MT-RJ)
                wsu4502gb(315),   -- 2 port 1000BaseX (GBIC)

                -- sub module 2 type for Cat6k modules
                wssvcidsupg(402),  -- IDS 2 accelerator board
                wssvccmm6e1(403),   -- 6 E1 port adapter
                wssvccmm6t1(404),   -- 6 T1 port adapter
                wssvccmm24fxs(405), -- 24 FXS port adapter
                wssvccmmact(406),   -- ad-hoc conferencing and
                                    -- transcoding port adapter
                wssvcpisa32(597),   -- PISA card (Multilayer switch &
                                    -- service feature card)
                me6524msfc2a(598),  -- Multilayer switch feature
                                    -- card II A
                wsf6kmsfc2a(599), -- Multilayer switch feature card II A

                -- sub module 2 type for sup 720
                wssup720(1001),     -- Supervisor Mod 720 CPU board
                vsf6kmsfc3(1026),   -- Supervisor Mod 720 10G CPU board

                -- 7600 only module
                esm2x10ge(1701),    -- CPU Daughterboard for esm2x10ge
                c7600msfc4(1805)    -- 7600 MSFC4 cpu daughtercard
                }
        MAX-ACCESS    read-only
        STATUS        current
        DESCRIPTION   "The type of daughterboard attached to this
                      module."
        ::= { moduleEntry 24 }

moduleSlotNum OBJECT-TYPE
        SYNTAX        INTEGER (1..16)
        MAX-ACCESS    read-only
        STATUS        current
        DESCRIPTION   "This value is determined by the chassis slot
                      number where the module is located. Valid entries
                      are 1 to the value of chassisNumSlots"
        ::= { moduleEntry 25 }

moduleSerialNumberString OBJECT-TYPE
        SYNTAX        DisplayString (SIZE (0..20))
        MAX-ACCESS    read-only
        STATUS        current
        DESCRIPTION   "The serial number of the module. This MIB object
                       will return the module serial number for any
                       module that either a numeric or an alphanumeric
                       serial number is being used."
        ::= { moduleEntry 26 }

moduleEntPhysicalIndex OBJECT-TYPE
        SYNTAX  PhysicalIndex
        MAX-ACCESS      read-only
        STATUS          current
        DESCRIPTION   "The value of the instance of the entPhysicalIndex
                      object, defined in ENTITY-MIB, for the entity
                      physical index corresponding to this module."
        ::= { moduleEntry 27 }

moduleAdditionalStatus OBJECT-TYPE
        SYNTAX       BITS {
                            fruInstalled(0),
                            powerDenied(1),
                            faulty(2)
                          }
        MAX-ACCESS   read-only
        STATUS       current
        DESCRIPTION  "The additional status of the module.

                      fruInstalled(0) indicates that whether or not
                      FRU is installed on the module.

                      powerDenied(1) indicates that whether phones
                      connected to the ports of this module are
                      denied of power.

                      faulty(2) indicates hardware faulty."
         ::= { moduleEntry 28}



-- the port group

-- Implementation of the port group is current for all Cisco Workgroup
-- Stack products.

portTable OBJECT-TYPE
        SYNTAX        SEQUENCE OF PortEntry
        MAX-ACCESS    not-accessible
        STATUS        current
        DESCRIPTION   "A list of port entries. The number of entries is
                      determined by the number of modules in the chassis
                      and the number of ports on each module."
        ::= { portGrp 1 }

portEntry OBJECT-TYPE
        SYNTAX        PortEntry
        MAX-ACCESS    not-accessible
        STATUS        current
        DESCRIPTION   "Entry containing information for a particular
                      port on a module."
        INDEX         { portModuleIndex, portIndex }
        ::= { portTable 1 }

PortEntry ::=
        SEQUENCE {
                portModuleIndex
                        INTEGER,
                portIndex
                        INTEGER,
                portCrossIndex
                        INTEGER,
                portName
                        DisplayString,
                portType
                        INTEGER,
                portOperStatus
                        INTEGER,
                portCrossGroupIndex
                        INTEGER,
                portAdditionalStatus
                        INTEGER,
                portAdminSpeed
                        INTEGER,
                portDuplex
                        INTEGER,
                portIfIndex
                        INTEGER,
                portSpantreeFastStart
                        INTEGER,
                portAdminRxFlowControl
                        INTEGER,
                portOperRxFlowControl
                        INTEGER,
                portAdminTxFlowControl
                        INTEGER,
                portOperTxFlowControl
                        INTEGER,
                portMacControlTransmitFrames
                        Counter32,
                portMacControlReceiveFrames
                        Counter32,
                portMacControlPauseTransmitFrames
                        Counter32,
                portMacControlPauseReceiveFrames
                        Counter32,
                portMacControlUnknownProtocolFrames
                        Counter32,
                portLinkFaultStatus
                        INTEGER,
                portAdditionalOperStatus
                        BITS,
                portInlinePowerDetect
                        TruthValue,
                portEntPhysicalIndex
                        PhysicalIndex,
                portErrDisableTimeOutEnable
                        INTEGER
        }

portModuleIndex OBJECT-TYPE
        SYNTAX        INTEGER (1..16)
        MAX-ACCESS    read-only
        STATUS        current
        DESCRIPTION   "An index value that uniquely identifies the
                      module where this port is located."
        ::= { portEntry 1 }

portIndex OBJECT-TYPE
        SYNTAX        INTEGER (1..255)
        MAX-ACCESS    read-only
        STATUS        current
        DESCRIPTION   "An index value that uniquely identifies this port
                      within a module. The value is determined by the
                      location of the port on the module. Valid entries
                      are 1 to the value of moduleNumPorts for this
                      module."
        ::= { portEntry 2 }

portCrossIndex OBJECT-TYPE
        SYNTAX        INTEGER (1..4080)
        MAX-ACCESS    read-only
        STATUS        current
        DESCRIPTION   "A cross-reference to the port's index within
                      another mib group. The value is dependent on the
                      type of port. For an FDDI port, this corresponds
                      to the snmpFddiPORTIndex."
        ::= { portEntry 3 }

portName OBJECT-TYPE
        SYNTAX        DisplayString (SIZE (0..20))
        MAX-ACCESS    read-write
        STATUS        current
        DESCRIPTION   "A descriptive string used by the network
                      administrator to name the port."
        ::= { portEntry 4 }

portType OBJECT-TYPE
        SYNTAX        INTEGER {
                            other(1),      -- none of the following
                            cddi(2),       -- CDDI (UTP FDDI)
                            fddi(3),       -- Multi Mode fiber FDDI
                            tppmd(4),      -- ANSI standard UTP FDDI
                            mlt3(5),       -- MLT-3 UTP FDDI
                            sddi(6),       -- STP FDDI
                            smf(7),        -- Single Mode fiber FDDI
                            e10BaseT(8),   -- UTP Ethernet
                            e10BaseF(9),   -- Multi Mode fiber Ethernet
                            scf(10),       -- small-connector fiber FDDI
                            e100BaseTX(11),-- UTP Fast Ethernet (Cat 5)
                            e100BaseT4(12),-- UTP Fast Ethernet (Cat 3)
                            e100BaseF(13), -- Multi Mode fiber Fast
                                           -- Ethernet
                            atmOc3mmf(14), -- Multi Mode fiber OC-3 ATM
                            atmOc3smf(15), -- Single Mode fiber OC-3 ATM
                            atmOc3utp(16), -- UTP OC-3 ATM
                            e100BaseFsm(17), -- Single Mode fiber Fast
                                             -- Ethernet
                            e10a100BaseTX(18), -- 10/100 UTP Ethernet
                                               -- (Cat 3/5)
                            mii(19),        -- MII Ethernet
                            vlanRouter(20), -- vlan router connection
                            remoteRouter(21), --
                            tokenring(22), -- Token Ring
                            atmOc12mmf(23),-- Multi Mode fiber OC-12 ATM
                            atmOc12smf(24),-- Single Mode fiber OC-12
                                           -- ATM
                            atmDs3(25),    -- DS-3 ATM
                            tokenringMmf(26), -- Multi Mode fiber Token
                                              -- Ring
                            e1000BaseLX(27), -- Long Wave fiber Giga
                                             -- Ethernet
                            e1000BaseSX(28), -- Short Wave fiber Giga
                                             -- Ethernet
                            e1000BaseCX(29), -- Copper Gigabit Ethernet
                            networkAnalysis(30), -- Network Analysis
                                                 -- connection
                            e1000Empty(31),  -- GBIC not installed
                            e1000BaseLH(32), -- Long Haul fiber Giga
                                             -- Ethernet
                            e1000BaseT(33),  -- Twisted Pair Giga
                                             -- Ethernet
                            e1000UnsupportedGbic(34),
                                             -- Unsupported Gbic Giga
                                             -- Ethernet
                            e1000BaseZX(35), -- Extended Reach Giga
                                             -- Ethernet
                            depi2(36),       -- Digital Ethernet Phone
                                             -- Interface 2 Mbps
                            t1(37),          -- T1
                            e1(38),          -- E1
                            fxs(39),         -- FXS
                            fxo(40),         -- FXO
                            transcoding(41), -- transcoding DSP
                            conferencing(42),-- conferencing DSP
                            atmOc12mm(43),   -- OC-12 ATM MMF
                            atmOc12smi(44),  -- OC-12 ATM SMIR
                            atmOc12sml(45),  -- OC-12 ATM SML
                            posOc12mm(46),   -- OC-12 POS MM
                            posOc12smi(47),  -- OC-12 POS SMIR
                            posOc12sml(48),  -- OC-12 POS SMLR
                            posOc48sms(49),  -- OC-48 POS SMS
                            posOc48smi(50),  -- OC-48 POS SMIR
                            posOc48sml(51),  -- OC-48 POS SMLR
                            posOc3mm(52),    -- OC-3 POS MM
                            posOc3smi(53),   -- OC-3 POS SMIR
                            posOc3sml(54),   -- OC-3 POS SMLR
                            intrusionDetect(55), -- intrusion detection
                            e10GBaseCPX(56), --10GE Parallel 860nm Laser
                            e10GBaseLX4(57), -- 10GE Wide-WDM 1310nm
                                             -- Laser
                            e10GBaseEX4(59), -- 10GE Wide-WDM 1550 Laser
                            e10GEmpty(60),   -- 10GE not installed
                            e10a100a1000BaseT(61), -- 10/100/1000 BaseT
                            dptOc48mm(62),   -- OC-48 DPT MM
                            dptOc48smi(63),  -- OC-48 DPT SMIR
                            dptOc48sml(64),  -- OC-48 DPT SMLR
                            e10GBaseLR(65),  -- 10GE Serial 1310nm Laser
                            chOc12smi(66),   -- OC-12 channelized SMIR
                            chOc12mm(67),    -- OC-12 channelized MM
                            chOc48ss(68),    -- OC-48 channelized SS
                            chOc48smi(69),   -- OC-48 channelized SMIR
                            e10GBaseSX4(70), -- 10GE Wide-WDM 850nm
                                             -- Laser
                            e10GBaseER(71),  -- 10GE Serial 1550nm Laser
                            contentEngine(72),-- content engine
                                              -- connection
                            ssl(73),          -- SSL connection
                            firewall(74),     -- Firewall connection
                            vpnIpSec(75),     -- VPN IP Sec connection
                            ct3(76),          -- DS3 Channelized
                            e1000BaseCwdm1470(77),
                                             -- CWDM 1470 Giga Ethernet
                            e1000BaseCwdm1490(78),
                                             -- CWDM 1490 Giga Ethernet
                            e1000BaseCwdm1510(79),
                                             -- CWDM 1510 Giga Ethernet
                            e1000BaseCwdm1530(80),
                                             -- CWDM 1530 Giga Ethernet
                            e1000BaseCwdm1550(81),
                                             -- CWDM 1550 Giga Ethernet
                            e1000BaseCwdm1570(82),
                                             -- CWDM 1570 Giga Ethernet
                            e1000BaseCwdm1590(83),
                                             -- CWDM 1590 Giga Ethernet
                            e1000BaseCwdm1610(84),
                                             -- CWDM 1610 Giga Ethernet
                            e1000BaseBT(85), -- BT Giga Ethernet
                            e1000BaseUnapproved(86),
                                             -- Unappeoved Giga Ethernet
                            chOc3smi(87),    -- OC-3 channelized SMIR
                            mcr(88),  -- Mobile Context Registry
                                      -- connection
                            coe(89),  -- Content Optimization Engine
                                      -- connection
                            mwa(90),  -- Mobile Wireless Application
                                      -- connection
                            psd(91),  -- Persistent Store Device
                                      -- connection
                            e100BaseLX(92),  -- Long Wave fiber Fast
                                             -- Ethernet
                            e10GBaseSR(93),  -- 10GE Serial 850nm Laser
                            e10GBaseCX4(94), -- 10GE XAUI Copper
                            e10GBaseWdm1550(95),
                                       -- 10GE Serial 1550nm Laser
                            e10GBaseEdc1310(96),
                                       -- 10GE Serial 1310nm EDC Laser
                            e10GBaseSW(97),  -- 10GE Laser
                            e10GBaseLW(98),  -- 10GE Laser
                            e10GBaseEW(99),  -- 10GE Laser
                            lwa(100),  -- Lan Wireless Application
                                       -- connection
                            aons(101), -- Application Oriented Network
                                       -- Switching
                            sslVpn(102), -- Web/VPN
                            e100BaseEmpty(103),   -- Fiber Fast Ethernet
                                                  -- not installed
                            adsm(104), -- Distributed Denial of Service
                                       -- Detector
                            agsm(105), -- Distributed Denial of Service
                                       -- Guard
                            aces(106), -- Application Control Engine
                                       -- Service
                            intrusionProtect(109), -- intrusion protection
                            e1000BaseSvc(110), -- Service Module Giga Ethernet
                            e10GBaseSvc(111),  -- Service Module 10G Ethernet
                            e1000BaseUnknown(1000),
                                             -- Unknown Giga Ethernet
                            e10GBaseUnknown(1001),    -- Unknown 10G
                            e10GBaseUnapproved(1002), -- Unapproved 10G

                            e1000BaseWdmRxOnly(1003),
                                             -- WDM Rx ONLY Giga Ether
                            e1000BaseDwdm3033(1004),
                                            -- DWDM 3033 Giga Ethernet
                            e1000BaseDwdm3112(1005),
                                            -- DWDM 3112 Giga Ethernet
                            e1000BaseDwdm3190(1006),
                                            -- DWDM 3190 Giga Ethernet
                            e1000BaseDwdm3268(1007),
                                            -- DWDM 3268 Giga Ethernet
                            e1000BaseDwdm3425(1008),
                                            -- DWDM 3425 Giga Ethernet
                            e1000BaseDwdm3504(1009),
                                            -- DWDM 3504 Giga Ethernet
                            e1000BaseDwdm3582(1010),
                                            -- DWDM 3582 Giga Ethernet
                            e1000BaseDwdm3661(1011),
                                            -- DWDM 3661 Giga Ethernet
                            e1000BaseDwdm3819(1012),
                                            -- DWDM 3819 Giga Ethernet
                            e1000BaseDwdm3898(1013),
                                            -- DWDM 3898 Giga Ethernet
                            e1000BaseDwdm3977(1014),
                                            -- DWDM 3977 Giga Ethernet
                            e1000BaseDwdm4056(1015),
                                            -- DWDM 4056 Giga Ethernet
                            e1000BaseDwdm4214(1016),
                                            -- DWDM 4214 Giga Ethernet
                            e1000BaseDwdm4294(1017),
                                            -- DWDM 4294 Giga Ethernet
                            e1000BaseDwdm4373(1018),
                                            -- DWDM 4373 Giga Ethernet
                            e1000BaseDwdm4453(1019),
                                            -- DWDM 4453 Giga Ethernet
                            e1000BaseDwdm4612(1020),
                                            -- DWDM 4612 Giga Ethernet
                            e1000BaseDwdm4692(1021),
                                            -- DWDM 4692 Giga Ethernet
                            e1000BaseDwdm4772(1022),
                                            -- DWDM 4772 Giga Ethernet
                            e1000BaseDwdm4851(1023),
                                            -- DWDM 4851 Giga Ethernet
                            e1000BaseDwdm5012(1024),
                                            -- DWDM 5012 Giga Ethernet
                            e1000BaseDwdm5092(1025),
                                            -- DWDM 5092 Giga Ethernet
                            e1000BaseDwdm5172(1026),
                                            -- DWDM 5172 Giga Ethernet
                            e1000BaseDwdm5252(1027),
                                            -- DWDM 5252 Giga Ethernet
                            e1000BaseDwdm5413(1028),
                                            -- DWDM 5413 Giga Ethernet
                            e1000BaseDwdm5494(1029),
                                            -- DWDM 5494 Giga Ethernet
                            e1000BaseDwdm5575(1030),
                                            -- DWDM 5575 Giga Ethernet
                            e1000BaseDwdm5655(1031),
                                            -- DWDM 5655 Giga Ethernet
                            e1000BaseDwdm5817(1032),
                                            -- DWDM 5817 Giga Ethernet
                            e1000BaseDwdm5898(1033),
                                            -- DWDM 5898 Giga Ethernet
                            e1000BaseDwdm5979(1034),
                                            -- DWDM 5979 Giga Ethernet
                            e1000BaseDwdm6061(1035),
                                            -- DWDM 6061 Giga Ethernet

                            e10GBaseWdmRxOnly(1036),
                                            -- DWDM 10G WDM Rx ONLY
                            e10GBaseDwdm3033(1037),
                                            -- DWDM 10G 3033 Laser
                            e10GBaseDwdm3112(1038),
                                            -- DWDM 10G 3112 Laser
                            e10GBaseDwdm3190(1039),
                                            -- DWDM 10G 3190 Laser
                            e10GBaseDwdm3268(1040),
                                            -- DWDM 10G 3268 Laser
                            e10GBaseDwdm3425(1041),
                                            -- DWDM 10G 3425 Laser
                            e10GBaseDwdm3504(1042),
                                            -- DWDM 10G 3504 Laser
                            e10GBaseDwdm3582(1043),
                                            -- DWDM 10G 3582 Laser
                            e10GBaseDwdm3661(1044),
                                            -- DWDM 10G 3661 Laser
                            e10GBaseDwdm3819(1045),
                                            -- DWDM 10G 3819 Laser
                            e10GBaseDwdm3898(1046),
                                            -- DWDM 10G 3898 Laser
                            e10GBaseDwdm3977(1047),
                                            -- DWDM 10G 3977 Laser
                            e10GBaseDwdm4056(1048),
                                            -- DWDM 10G 4056 Laser
                            e10GBaseDwdm4214(1049),
                                            -- DWDM 10G 4214 Laser
                            e10GBaseDwdm4294(1050),
                                            -- DWDM 10G 4294 Laser
                            e10GBaseDwdm4373(1051),
                                            -- DWDM 10G 4373 Laser
                            e10GBaseDwdm4453(1052),
                                            -- DWDM 10G 4453 Laser
                            e10GBaseDwdm4612(1053),
                                            -- DWDM 10G 4612 Laser
                            e10GBaseDwdm4692(1054),
                                            -- DWDM 10G 4692 Laser
                            e10GBaseDwdm4772(1055),
                                            -- DWDM 10G 4772 Laser
                            e10GBaseDwdm4851(1056),
                                            -- DWDM 10G 4851 Laser
                            e10GBaseDwdm5012(1057),
                                            -- DWDM 10G 5012 Laser
                            e10GBaseDwdm5092(1058),
                                            -- DWDM 10G 5092 Laser
                            e10GBaseDwdm5172(1059),
                                            -- DWDM 10G 5172 Laser
                            e10GBaseDwdm5252(1060),
                                            -- DWDM 10G 5252 Laser
                            e10GBaseDwdm5413(1061),
                                            -- DWDM 10G 5413 Laser
                            e10GBaseDwdm5494(1062),
                                            -- DWDM 10G 5494 Laser
                            e10GBaseDwdm5575(1063),
                                            -- DWDM 10G 5575 Laser
                            e10GBaseDwdm5655(1064),
                                            -- DWDM 10G 5655 Laser
                            e10GBaseDwdm5817(1065),
                                            -- DWDM 10G 5817 Laser
                            e10GBaseDwdm5898(1066),
                                            -- DWDM 10G 5898 Laser
                            e10GBaseDwdm5979(1067),
                                            -- DWDM 10G 5979 Laser
                            e10GBaseDwdm6061(1068),
                                            -- DWDM 10G 6061 Laser
                            e1000BaseBX10D(1069),
                                 -- Giga Ethernet bi-directional 10km
                                 -- Downlink over SMF
                            e1000BaseBX10U(1070),
                                 -- Giga Ethernet bi-directional 10km
                                 -- Uplink over SMF
                            e100BaseUnknown(1071),
                                 -- Unknown Fiber Fast Ethernet
                            e100BaseUnapproved(1072),
                                 -- Unapproved Fiber Fast Ethernet
                            e100BaseSX(1073),
                                 -- Short Wave Fiber Fast Ethernet
                            e100BaseBX10D(1074),
                                 -- Fiber Fast Ethernet bi-directional
                                 -- 10km Downlink over SMF
                            e100BaseBX10U(1075),
                                 -- Fiber Fast Ethernet bi-directional
                                 -- 10km Uplink over SMF
                            e10GBaseBad(1076),    -- Bad 10G
                            e10GBaseZR(1077),     -- 10GE Laser
                            e100BaseEX(1078),
                                 -- Fiber Fast Ethernet
                            e100BaseZX(1079),
                                 -- Extended Reach Fiber Fast Ethernet
                            e10GBaseLRM(1080),
                                 -- 10GE Laser 300m over 50um Multi Mode Fiber
                            e10GBaseT(1081)
                                 -- 10GE Laser twisted pair
                                }
        MAX-ACCESS    read-only
        STATUS        current
        DESCRIPTION   "The type of physical layer medium dependent
                      interface on the port."
        ::= { portEntry 5 }

portOperStatus OBJECT-TYPE
        SYNTAX        INTEGER {
                                other(1),       -- none of the following
                                ok(2),          -- status ok
                                minorFault(3),  -- minor problem
                                majorFault(4)   -- major problem
                                }
        MAX-ACCESS    read-only
        STATUS        current
        DESCRIPTION   "The current operational status of the port."
        ::= { portEntry 6 }

portCrossGroupIndex OBJECT-TYPE
        SYNTAX        INTEGER (1..16)
        MAX-ACCESS    read-only
        STATUS        current
        DESCRIPTION   "A cross-reference to another mib group for this
                      port. The value is dependent on the type of port.
                      For an FDDI port this corresponds to the
                      snmpFddiPORTSMTIndex."
        ::= { portEntry 7 }

portAdditionalStatus OBJECT-TYPE
        SYNTAX        INTEGER (0..7)
        MAX-ACCESS    read-only
        STATUS        current
        DESCRIPTION   "Additional status information for the port. The
                      value is a sum. It initially takes the value zero,
                      then for each state that is true, 2 raised to a
                      power is added to the sum. The powers are
                      according to the following table:
                               State    Power
                            Transmit    0
                             Receive    1
                           Collision    2
                      Transmit state indicates that at least one packet
                      was transmitted by the port in the last polling
                      period. Receive state indicates that at least one
                      packet was received by the port in the last
                      polling period. Collision state indicates that
                      at least one collision was detected on the port
                      in the last polling period.
                      Note that if a state is not applicable to a
                      particular port or additional status is not
                      supported on a particular port, its value is
                      always false for that port."
        ::= { portEntry 8 }

portAdminSpeed OBJECT-TYPE
        SYNTAX        INTEGER {
                                autoDetect(1),
                                autoDetect10100(2),
                                       -- Auto Detect with,
                                       -- only allowed values: 10 & 100
                                s4000000(4000000),       -- 4 Mbps
                                s10000000(10000000),     -- 10 Mbps
                                s16000000(16000000),     -- 16 Mbps
                                s45000000(45000000),     -- 45 Mbps
                                s64000000(64000000),     -- 64 Mbps
                                s100000000(100000000),   -- 100 Mbps
                                s155000000(155000000),   -- 155 Mbps
                                s400000000(400000000),   -- 400 Mbps
                                s622000000(622000000),   -- 622 Mbps
                                s1000000000(1000000000), -- 1 Gbps
                                s1544000(1544000),       -- 1.544 Mbps
                                s2000000(2000000),       -- 2 Mbps
                                s2048000(2048000),       -- 2.048 Mbps
                                s64000(64000),           -- 64 kps
                                s10G(10)                 -- 10 Gps
                                }
        MAX-ACCESS    read-write
        STATUS        current
        DESCRIPTION   "The desired speed of the port.
                      The current operational speed of the port can be
                      determined from ifSpeed."
        ::= { portEntry 9 }

portDuplex OBJECT-TYPE
        SYNTAX        INTEGER {
                                half(1),
                                full(2),
                                disagree(3), -- read-only
                                auto(4)      -- read-only
                              }
        MAX-ACCESS    read-write
        STATUS        current
        DESCRIPTION   "Indicates whether the port is operating in half-
                      duplex, full-duplex, disagree or auto negotiation
                      mode. If the port could not agree with the far end
                      on port duplex, the port will be in disagree(3)
                      mode."
        ::= { portEntry 10 }

portIfIndex OBJECT-TYPE
        SYNTAX        INTEGER (1..2147483647)
        MAX-ACCESS    read-only
        STATUS        current
        DESCRIPTION   "The value of the instance of the ifIndex object,
                      defined in MIB-II, for the interface corresponding
                      to this port."
        ::= { portEntry 11 }

portSpantreeFastStart OBJECT-TYPE
        SYNTAX        INTEGER { enabled(1), disabled(2) }
        MAX-ACCESS    read-write
        STATUS        deprecated
        DESCRIPTION   "Indicates whether the port is operating in
                      spantree fast start mode. A port with fast start
                      enabled is immediately put in spanning tree
                      forwarding state on link up, rather than starting
                      in blocking state which is the normal operation.
                      This is useful when the port is known to be
                      connected to a single station which has problems
                      waiting for the normal spanning tree operation to
                      put the port in forwarding state.

                      This object is deprecated and replaced by
                      stpxFastStartPortTable in
                      CISCO-STP-EXTENSIONS-MIB."
        DEFVAL { disabled }
        ::= { portEntry 12 }

portAdminRxFlowControl OBJECT-TYPE
        SYNTAX        INTEGER { on(1), off(2), desired(3) }
        MAX-ACCESS    read-write
        STATUS        current
        DESCRIPTION   "Indicates the receive flow control administrative
                      status set on the port. If the status is set to
                      on(1), the port will require the far end to send
                      flow control. If the status is set to off(2), the
                      port will not allow far end to send flow control.
                      If the status is set to desired(3), the port will
                      allow the far end to send the flow control."
        DEFVAL { off }
        ::= { portEntry 13}

portOperRxFlowControl OBJECT-TYPE
        SYNTAX        INTEGER { on(1), off(2), disagree(3) }
        MAX-ACCESS    read-only
        STATUS        current
        DESCRIPTION   "Indicates the receive flow control operational
                      status of the port. If the port could not agree
                      with the far end on a link protocol, its
                      operational status will be disagree(3)."
        ::= { portEntry 14}

portAdminTxFlowControl OBJECT-TYPE
        SYNTAX        INTEGER { on(1), off(2), desired(3) }
        MAX-ACCESS    read-write
        STATUS        current
        DESCRIPTION   "Indicates the transmit flow control
                      administrative status set on the port.
                      If the status is set to on(1), the port will send
                      flow control to the far end.
                      If the status is set to off(2), the port will not
                      send flow control to the far end. If the status is
                      set to desired(3), the port will send flow control
                      to the far end if the far end supports it."
        ::= { portEntry 15}

portOperTxFlowControl OBJECT-TYPE
        SYNTAX        INTEGER { on(1), off(2), disagree(3) }
        MAX-ACCESS    read-only
        STATUS        current
        DESCRIPTION   "Indicates the transmit flow control operational
                      status of the port. If the port could not agree
                      with the far end on a link protocol, its
                      operational status will be disagree(3)."
        ::= { portEntry 16}

portMacControlTransmitFrames OBJECT-TYPE
        SYNTAX        Counter32
        MAX-ACCESS    read-only
        STATUS        current
        DESCRIPTION   "The total number of MAC control frames passed to
                      the MAC sublayer for transmission."
        ::= { portEntry 17}

portMacControlReceiveFrames OBJECT-TYPE
        SYNTAX        Counter32
        MAX-ACCESS    read-only
        STATUS        current
        DESCRIPTION   "The total number of MAC control frames passed by
                      the MAC sublayer to the MAC Control sublayer on
                      receive."
        ::= { portEntry 18}

portMacControlPauseTransmitFrames OBJECT-TYPE
        SYNTAX        Counter32
        MAX-ACCESS    read-only
        STATUS        current
        DESCRIPTION   "The total number of PAUSE frames passed to
                      the MAC sublayer for transmission."
        ::= { portEntry 19}

portMacControlPauseReceiveFrames OBJECT-TYPE
        SYNTAX        Counter32
        MAX-ACCESS    read-only
        STATUS        current
        DESCRIPTION   "The total number of PAUSE frames passed by
                      the MAC sublayer to the MAC Control sublayer
                      on receive."
        ::= { portEntry 20}

portMacControlUnknownProtocolFrames OBJECT-TYPE
        SYNTAX        Counter32
        MAX-ACCESS    read-only
        STATUS        current
        DESCRIPTION   "The total number of MAC Control frames received
                      with an opcode that is not supported by the
                      device."
        ::= { portEntry 21}

portLinkFaultStatus OBJECT-TYPE
        SYNTAX        INTEGER {
                                noFault(1),
                                nearEndFault(2),
                                nearEndConfigFail(3),
                                farEndDisable(4),
                                farEndFault(5),
                                farEndConfigFail(6),
                                notApplicable(7)
                              }
        MAX-ACCESS    read-only
        STATUS        current
        DESCRIPTION   "Specifies additional link fault status on a
                      gigabit link.

                      noFault:
                              Link is up and operational.
                      nearEndFault:
                              The port is enabled but there is no GBIC
                              present or the local port cannot
                              synchronize with the remote end.
                      nearEndConfigFail:
                              The local port has detected a
                              configuration mismatch with the remote
                              end.
                      farEndDisable:
                              The far end is in the disabled state.
                      farEndFault:
                              The remote port is cannot synchronize.
                      farEndConfigFail:
                              The remote port has detected a
                              configuration mismatch with the local end.
                      notApplicable:
                              Link fault status is not applicable on
                              this port."
        ::= { portEntry 22 }

portAdditionalOperStatus OBJECT-TYPE
        SYNTAX        BITS {
                                other(0),       -- none of the following
                                connected(1),
                                standby(2),
                                faulty(3),
                                notConnected(4),
                                inactive(5),
                                shutdown(6),
                                dripDis(7),
                                disabled(8),
                                monitor(9),
                                errdisable(10),
                                linkFaulty(11),
                                onHook(12),
                                offHook(13),
                                reflector(14)
                                }
        MAX-ACCESS    read-only
        STATUS        current
        DESCRIPTION   "The current operational status of the port which
                      is showing additional detailed information of the
                      port."
        ::= { portEntry 23 }

portInlinePowerDetect OBJECT-TYPE
        SYNTAX  TruthValue
        MAX-ACCESS      read-only
        STATUS          current
        DESCRIPTION
            "Indicate if the port detects an inline power capable
             device connected to it."
        ::= { portEntry 24 }

portEntPhysicalIndex OBJECT-TYPE
        SYNTAX  PhysicalIndex
        MAX-ACCESS      read-only
        STATUS          current
        DESCRIPTION   "The value of the instance of the entPhysicalIndex
                      object, defined in ENTITY-MIB, for the
                      entity physical index corresponding to this port."
        ::= { portEntry 25 }

portErrDisableTimeOutEnable OBJECT-TYPE
        SYNTAX  INTEGER { enabled(1), disabled(2) }
        MAX-ACCESS      read-write
        STATUS          current
        DESCRIPTION   "Indicates whether a port that is put into
                      errdisable state by a cause as specified by
                      sysErrDisableTimeoutEnable will be re-enabled
                      automatically during the timeout interval as
                      specified by sysErrDisableTimeoutInterval."
        DEFVAL  { enabled }
        ::= { portEntry 26 }


-- the tftp group

-- Implementation of the tftp group is current for all Cisco Workgroup
-- Stack products which implement tftp upload/download functions.

tftpHost OBJECT-TYPE
        SYNTAX        DisplayString (SIZE (0..64))
        MAX-ACCESS    read-write
        STATUS        current
        DESCRIPTION   "Name of source/destination host for the TFTP
                      transfer or storage device transfer. If the name
                      is for the TFTP transfer, it can be the IP
                      address or the host name. If the name for the
                      storage device transfer, it will be in the format
                      of deviceName: (e.g. slot0:, slot1:)."
        ::= { tftpGrp 1 }

tftpFile OBJECT-TYPE
        SYNTAX        DisplayString (SIZE (0..64))
        MAX-ACCESS    read-write
        STATUS        current
        DESCRIPTION   "Name of file for the TFTP transfer or for storage
                       device transfer."
        ::= { tftpGrp 2 }

tftpModule OBJECT-TYPE
        SYNTAX        INTEGER (0..16)
        MAX-ACCESS    read-write
        STATUS        current
        DESCRIPTION   "Which module's code/configuration is being
                      transferred."
        ::= { tftpGrp 3 }

tftpAction OBJECT-TYPE
        SYNTAX        INTEGER {
                                other(1),       -- none of the following
                                downloadConfig(2),
                                uploadConfig(3),
                                downloadSw(4),
                                uploadSw(5),
                                downloadFw(6),
                                uploadFw(7)
                              }
        MAX-ACCESS    read-write
        STATUS        current
        DESCRIPTION   "Setting this object to one of the acceptable
                      values initiates the requested action using the
                      information given in tftpHost, tftpFile,
                      tftpModule.

                          downloadConfig(2): receive configuration from
                                             host/file
                          uploadConfig(3)  : send configuration to
                                             host/file
                          downloadSw(4)    : receive software image from
                                             host/file
                          uploadSw(5)      : send software image to
                                             host/file
                          downloadFw(6)    : receive firmware image from
                                             host/file
                          uploadFw(7)      : send firmware image to
                                             host/file
                      Setting this object to any other value results in
                      an error."
        ::= { tftpGrp 4 }

tftpResult OBJECT-TYPE
        SYNTAX        INTEGER {
                                inProgress(1),
                                success(2),
                                noResponse(3),
                                tooManyRetries(4),
                                noBuffers(5),
                                noProcesses(6),
                                badChecksum(7),
                                badLength(8),
                                badFlash(9),
                                serverError(10),
                                userCanceled(11),
                                wrongCode(12),
                                fileNotFound(13),
                                invalidTftpHost(14),
                                invalidTftpModule(15),
                                accessViolation(16),
                                unknownStatus(17),
                                invalidStorageDevice(18),
                                insufficientSpaceOnStorageDevice(19),
                                insufficientDramSize(20),
                                incompatibleImage(21)
                              }
        MAX-ACCESS    read-only
        STATUS        current
        DESCRIPTION   "Contains result of the last tftp action request."
        ::= { tftpGrp 5 }



-- the brouter group

--Implementation of the brouter group is current for all Cisco Workgroup
--Stack products which implement combined bridging/routing functions.

brouterEnableRip OBJECT-TYPE
        SYNTAX        INTEGER { enabled(1), disabled(2) }
        MAX-ACCESS    read-write
        STATUS        current
        DESCRIPTION   "Indicates whether the RIP protocol is enabled."
        DEFVAL { enabled }
        ::= { brouterGrp 1 }

brouterEnableSpantree OBJECT-TYPE
        SYNTAX        INTEGER { enabled(1), disabled(2) }
        MAX-ACCESS    read-write
        STATUS        current
        DESCRIPTION   "Indicates if Spanning Tree protocol is enabled."
        DEFVAL { disabled }
        ::= { brouterGrp 2 }

brouterEnableGiantCheck OBJECT-TYPE
        SYNTAX        INTEGER { enabled(1), disabled(2) }
        MAX-ACCESS    read-write
        STATUS        current
        DESCRIPTION   "Indicates whether special handling of giant
                      packets is enabled."
        DEFVAL { disabled }
        ::= { brouterGrp 3 }

brouterEnableIpFragmentation OBJECT-TYPE
        SYNTAX        INTEGER { enabled(1), disabled(2) }
        MAX-ACCESS    read-write
        STATUS        current
        DESCRIPTION   "Indicates whether IP fragmentation is enabled."
        DEFVAL { enabled }
        ::= { brouterGrp 4 }

brouterEnableUnreachables OBJECT-TYPE
        SYNTAX        INTEGER { enabled(1), disabled(2) }
        MAX-ACCESS    read-write
        STATUS        current
        DESCRIPTION   "Indicates whether ICMP unreachable messages are
                      sent by the system."
        DEFVAL { enabled }
        ::= { brouterGrp 5 }

brouterCamAgingTime OBJECT-TYPE
        SYNTAX        INTEGER (0..1000000)
        MAX-ACCESS    read-write
        STATUS        deprecated
        DESCRIPTION   "The aging time for the CAM table. This duplicate
                      item is the same value as dot1dTpAgingTime."
        DEFVAL { 300 }
        ::= { brouterGrp 6 }

brouterCamMode OBJECT-TYPE
        SYNTAX        INTEGER { filtering(1), forwarding(2) }
        MAX-ACCESS    read-write
        STATUS        current
        DESCRIPTION   "Mode in which the CAM module is operating."
        DEFVAL { filtering }
        ::= { brouterGrp 7 }

brouterIpxSnapToEther OBJECT-TYPE
        SYNTAX        INTEGER {
                                snap(1),
                                ethernetII(2),
                                iso8023(3),
                                raw8023(4)
                                }
        MAX-ACCESS    read-write
        STATUS        current
        DESCRIPTION   "The default translation for IPX packets when
                      bridging from FDDI SNAP to Ethernet."
        DEFVAL { raw8023 }
        ::= { brouterGrp 8 }

brouterIpx8023RawToFddi OBJECT-TYPE
        SYNTAX        INTEGER {
                                snap(1),
                                iso8022(5),
                                fddiRaw(6)
                                }
        MAX-ACCESS    read-write
        STATUS        current
        DESCRIPTION   "The default translation for IPX packets when
                      bridging from Ethernet 802.3 Raw to FDDI."
        DEFVAL { snap }
        ::= { brouterGrp 9 }

brouterEthernetReceiveMax OBJECT-TYPE
        SYNTAX        INTEGER (1..100)
        MAX-ACCESS    read-write
        STATUS        current
        DESCRIPTION   "Maximum number of Ethernet receive buffers
                      processed at one time per port."
        DEFVAL { 64 }
        ::= { brouterGrp 10 }

brouterEthernetTransmitMax OBJECT-TYPE
        SYNTAX        INTEGER (1..100)
        MAX-ACCESS    read-write
        STATUS        current
        DESCRIPTION   "Maximum number of Ethernet transmit buffers
                      processed at one time per port."
        DEFVAL { 64 }
        ::= { brouterGrp 11 }

brouterFddiReceiveMax OBJECT-TYPE
        SYNTAX        INTEGER (1..512)
        MAX-ACCESS    read-write
        STATUS        current
        DESCRIPTION   "Maximum number of FDDI receive buffers processed
                      at one time per port."
        DEFVAL { 256 }
        ::= { brouterGrp 12 }

brouterFddiTransmitMax OBJECT-TYPE
        SYNTAX        INTEGER (1..512)
        MAX-ACCESS    read-write
        STATUS        current
        DESCRIPTION   "Maximum number of FDDI transmit buffers processed
                      at one time per port."
        DEFVAL { 256 }
        ::= { brouterGrp 13 }

-- the brouter port table

brouterPortTable OBJECT-TYPE
        SYNTAX        SEQUENCE OF BrouterPortEntry
        MAX-ACCESS    not-accessible
        STATUS        current
        DESCRIPTION   "A list of brouter port entries. The number of
                      entries is determined by the number of modules in
                      the chassis and the number of ports on each
                      module."
        ::= { brouterGrp 14 }

brouterPortEntry OBJECT-TYPE
        SYNTAX        BrouterPortEntry
        MAX-ACCESS    not-accessible
        STATUS        current
        DESCRIPTION   "Entry containing bridge/router information for a
                      particular port on a module."
        INDEX         { brouterPortModule, brouterPort }
        ::= { brouterPortTable 1 }

BrouterPortEntry ::=
        SEQUENCE {
                brouterPortModule
                        INTEGER,
                brouterPort
                        INTEGER,
                brouterPortIpVlan
                        VlanIndex,
                brouterPortIpAddr
                        IpAddress,
                brouterPortNetMask
                        IpAddress,
                brouterPortBroadcast
                        IpAddress,
                brouterPortBridgeVlan
                        INTEGER,
                brouterPortIpHelpers
                        OCTET STRING
        }

brouterPortModule OBJECT-TYPE
        SYNTAX        INTEGER (1..16)
        MAX-ACCESS    read-only
        STATUS        current
        DESCRIPTION   "An index value that uniquely identifies the
                      module index where this port is located."
        ::= { brouterPortEntry 1 }

brouterPort OBJECT-TYPE
        SYNTAX        INTEGER (1..255)
        MAX-ACCESS    read-only
        STATUS        current
        DESCRIPTION   "An index value that uniquely identifies this port
                      within a module (see portIndex)."
        ::= { brouterPortEntry 2 }

brouterPortIpVlan OBJECT-TYPE
        SYNTAX        VlanIndex
        MAX-ACCESS    read-write
        STATUS        current
        DESCRIPTION   "The IP Virtual LAN to which this port belongs."
        ::= { brouterPortEntry 3 }

brouterPortIpAddr OBJECT-TYPE
        SYNTAX        IpAddress
        MAX-ACCESS    read-write
        STATUS        current
        DESCRIPTION   "This port's IP address."
        ::= { brouterPortEntry 4 }

brouterPortNetMask OBJECT-TYPE
        SYNTAX        IpAddress
        MAX-ACCESS    read-write
        STATUS        current
        DESCRIPTION   "This port's subnet mask."
        ::= { brouterPortEntry 5 }

brouterPortBroadcast OBJECT-TYPE
        SYNTAX        IpAddress
        MAX-ACCESS    read-write
        STATUS        current
        DESCRIPTION   "This port's broadcast address."
        ::= { brouterPortEntry 6 }

brouterPortBridgeVlan OBJECT-TYPE
        SYNTAX        INTEGER (0..1023)
        MAX-ACCESS    read-write
        STATUS        current
        DESCRIPTION   "The bridge Virtual LAN to which this port
                      belongs."
        ::= { brouterPortEntry 7 }

brouterPortIpHelpers OBJECT-TYPE
        SYNTAX        OCTET STRING (SIZE (0..128))
        MAX-ACCESS    read-write
        STATUS        current
        DESCRIPTION   "An indication of which other Virtual LANs UDP/IP
                      broadcasts received on this port will be forwarded
                      to. The normal situation is broadcasts NOT
                      forwarded beyond the originating VLAN, but it can
                      be useful in certain circumstances. This is an
                      octet string value with bits set to indicate
                      forwarded to VLANs. It can be interpreted as a sum
                      of f(x) as x goes from 0 to 1023, where f(x) = 0
                      for no forwarding to VLAN x and f(x) = exp(2, x)
                      for VLAN x forwarded to. If all bits are 0 or the
                      octet string is zero length, then UDP/IP
                      broadcasts are not being forwarded to other
                      VLANs."
        ::= { brouterPortEntry 8 }

-- additional brouter group objects

brouterIpx8022ToEther OBJECT-TYPE
        SYNTAX        INTEGER {
                                snap(1),
                                ethernetII(2),
                                iso8023(3),
                                raw8023(4)
                                }
        MAX-ACCESS    read-write
        STATUS        current
        DESCRIPTION   "The default translation for IPX packets when
                      bridging from FDDI 802.2 to Ethernet."
        DEFVAL { iso8023 }
        ::= { brouterGrp 15 }

brouterEnableTransitEncapsulation OBJECT-TYPE
        SYNTAX        INTEGER { enabled(1), disabled(2) }
        MAX-ACCESS    read-write
        STATUS        current
        DESCRIPTION   "Indicates whether Ethernet packets are
                      encapsulated on FDDI via transit encapsulation
                      protocol. Normally this option would be disabled
                      to allow translational bridging between Ethernet
                      and FDDI to take place."
        DEFVAL { disabled }
        ::= { brouterGrp 16 }

brouterEnableFddiCheck OBJECT-TYPE
        SYNTAX        INTEGER { enabled(1), disabled(2) }
        MAX-ACCESS    read-write
        STATUS        current
        DESCRIPTION   "Indicates whether MAC addresses learned one side
                      of a translational bridge should not be allowed to
                      be learned on the other side of the bridge. The
                      presence certain misbehaving devices on the
                      network may require this option to be enabled."
        DEFVAL { disabled }
        ::= { brouterGrp 17 }

brouterEnableAPaRT OBJECT-TYPE
        SYNTAX        INTEGER { enabled(1), disabled(2) }
        MAX-ACCESS    read-write
        STATUS        current
        DESCRIPTION   "Indicates whether the Automatic Packet
                      Recognition and Translation feature is enabled on
                      translational bridge(s) in the box. If APaRT is
                      disabled, the default translations as defined by
                      the objects brouterIpx8022ToEther,
                      brouterIpx8023RawToFddi, brouterIpxSnapToEther,
                      etc, are used on all packets and no automatic
                      learning of translation information is performed."
        DEFVAL { enabled }
        ::= { brouterGrp 18 }



-- the filter group

-- Implementation of the filter group is current for all Cisco Workgroup
-- Stack products which implement custom packet filtering functions.

-- the filter mac table

filterMacTable OBJECT-TYPE
        SYNTAX        SEQUENCE OF FilterMacEntry
        MAX-ACCESS    not-accessible
        STATUS        current
        DESCRIPTION   "A list of filter mac entries."
        ::= { filterGrp 1 }

filterMacEntry OBJECT-TYPE
        SYNTAX        FilterMacEntry
        MAX-ACCESS    not-accessible
        STATUS        current
        DESCRIPTION   "Entry containing MAC address filter information."
        INDEX         { filterMacModule, filterMacPort,
                        filterMacAddress }
        ::= { filterMacTable 1 }

FilterMacEntry ::=
        SEQUENCE {
                filterMacModule
                        INTEGER,
                filterMacPort
                        INTEGER,
                filterMacAddress
                        MacAddress,
                filterMacType
                        INTEGER
        }

filterMacModule OBJECT-TYPE
        SYNTAX        INTEGER (1..16)
        MAX-ACCESS    read-only
        STATUS        current
        DESCRIPTION   "An index value that uniquely identifies the
                      module where this port is located
                      (see portModuleIndex)."
        ::= { filterMacEntry 1 }

filterMacPort OBJECT-TYPE
        SYNTAX        INTEGER (1..255)
        MAX-ACCESS    read-only
        STATUS        current
        DESCRIPTION   "An index value that uniquely identifies this port
                      within a module (see portIndex)."
        ::= { filterMacEntry 2 }

filterMacAddress OBJECT-TYPE
        SYNTAX        MacAddress -- OCTET STRING (SIZE (6))
        MAX-ACCESS    read-only
        STATUS        current
        DESCRIPTION   "A MAC address. If the source or destination MAC
                      address equals this value, a match occurs. The
                      packet is dropped if a match occurs and deny(1)
                      was specified. The packet is dropped if a match
                      doesn't occur and at least one MAC address filter
                      was specified with permit(3)."
        ::= { filterMacEntry 3 }

filterMacType OBJECT-TYPE
        SYNTAX        INTEGER {
                         deny(1),         -- add deny entry
                         invalid(2),      -- remove this entry
                         permit(3),       -- add permit entry
                         permitSrc(4),    -- add permit source entry
                         permitDst(5),    -- add permit dest entry
                         denySrc(6),      -- add deny source entry
                         denyDst(7),      -- add deny dest entry
                         denySrcLearn(8)  -- add deny source learn entry
                      }
        MAX-ACCESS    read-write
        STATUS        current
        DESCRIPTION   "Setting this object to invalid(2) removes the
                      corresponding entry from the filterMacTable.
                      To add a new entry to the filterMacTable, set this
                      object to deny(1) or any value from permit(3) to
                      denySrcLearn(8) for a module, port, and MAC
                      address not already in the table."
        ::= { filterMacEntry 4 }

-- the filter vendor table

filterVendorTable OBJECT-TYPE
        SYNTAX        SEQUENCE OF FilterVendorEntry
        MAX-ACCESS    not-accessible
        STATUS        current
        DESCRIPTION   "A list of filter vendor ID entries."
        ::= { filterGrp 2 }

filterVendorEntry OBJECT-TYPE
        SYNTAX        FilterVendorEntry
        MAX-ACCESS    not-accessible
        STATUS        current
        DESCRIPTION   "Entry containing vendor ID filter information."
        INDEX         { filterVendorModule, filterVendorPort,
                        filterVendorId }
        ::= { filterVendorTable 1 }

FilterVendorEntry ::=
        SEQUENCE {
                filterVendorModule
                        INTEGER,
                filterVendorPort
                        INTEGER,
                filterVendorId
                        VendorIdType,
                filterVendorType
                        INTEGER
        }

filterVendorModule OBJECT-TYPE
        SYNTAX        INTEGER (1..16)
        MAX-ACCESS    read-only
        STATUS        current
        DESCRIPTION   "An index value that uniquely identifies the
                      module where this port is located
                      (see portModuleIndex)."
        ::= { filterVendorEntry 1 }

filterVendorPort OBJECT-TYPE
        SYNTAX        INTEGER (1..255)
        MAX-ACCESS    read-only
        STATUS        current
        DESCRIPTION   "An index value that uniquely identifies this port
                      within a module (see portIndex)."
        ::= { filterVendorEntry 2 }

filterVendorId OBJECT-TYPE
        SYNTAX        VendorIdType -- OCTET STRING (SIZE (3))
        MAX-ACCESS    read-only
        STATUS        current
        DESCRIPTION   "The vendor ID portion of a MAC address. If the
                      source or destination MAC address has the same
                      vendor ID, a match occurs. The packet is dropped
                      if a match occurs and deny(1) was specified. The
                      packet is dropped if a match doesn't occur and at
                      least one Vendor ID filter was specified with
                      permit(3)."
        ::= { filterVendorEntry 3 }

filterVendorType OBJECT-TYPE
        SYNTAX        INTEGER {
                                deny(1),         -- add deny entry
                                invalid(2),      -- remove this entry
                                permit(3)        -- add permit entry
                                }
        MAX-ACCESS    read-write
        STATUS        current
        DESCRIPTION   "Setting this object to invalid(2) removes the
                      corresponding entry from the filterVendorTable.
                      To add a new entry to the filterVendorTable, set
                      this object to deny(1) or permit(3) for a module,
                      port, and vendor ID not already in the table."
        ::= { filterVendorEntry 4 }

-- the filter protocol table

filterProtocolTable OBJECT-TYPE
        SYNTAX        SEQUENCE OF FilterProtocolEntry
        MAX-ACCESS    not-accessible
        STATUS        current
        DESCRIPTION   "A list of filter protocol entries."
        ::= { filterGrp 3 }

filterProtocolEntry OBJECT-TYPE
        SYNTAX        FilterProtocolEntry
        MAX-ACCESS    not-accessible
        STATUS        current
        DESCRIPTION   "Entry containing PROTOCOL address filter
                      information."
        INDEX         { filterProtocolModule, filterProtocolPort,
                        filterProtocolValue }
        ::= { filterProtocolTable 1 }

FilterProtocolEntry ::=
        SEQUENCE {
                filterProtocolModule
                        INTEGER,
                filterProtocolPort
                        INTEGER,
                filterProtocolValue
                        INTEGER,
                filterProtocolType
                        INTEGER
        }

filterProtocolModule OBJECT-TYPE
        SYNTAX        INTEGER (1..16)
        MAX-ACCESS    read-only
        STATUS        current
        DESCRIPTION   "An index value that uniquely identifies the
                      module where this port is located
                      (see portModuleIndex)."
        ::= { filterProtocolEntry 1 }

filterProtocolPort OBJECT-TYPE
        SYNTAX        INTEGER (1..255)
        MAX-ACCESS    read-only
        STATUS        current
        DESCRIPTION   "An index value that uniquely identifies this port
                      within a module (see portIndex)."
        ::= { filterProtocolEntry 2 }

filterProtocolValue OBJECT-TYPE
        SYNTAX        INTEGER (0..65535)
        MAX-ACCESS    read-only
        STATUS        current
        DESCRIPTION   "A 16-bit protocol value. If the packet's type
                      field or the packet's DSAP/SSAP field is equal to
                      this value, a match occurs. The packet is dropped
                      if a match occurs and deny(1) was specified. The
                      packet is dropped if a match doesn't occur and at
                      least one protocol type filter was specified with
                      permit(3)."
        ::= { filterProtocolEntry 3 }

filterProtocolType OBJECT-TYPE
        SYNTAX        INTEGER {
                                deny(1),         -- add deny entry
                                invalid(2),      -- remove this entry
                                permit(3)        -- add permit entry
                                }
        MAX-ACCESS    read-create
        STATUS        current
        DESCRIPTION   "Setting this object to invalid(2) removes the
                      corresponding entry from the filterProtocolTable.
                      To add a new entry to the filterProtocolTable, set
                      this object to deny(1) or permit(3) for a module,
                      port, and protocol value not already in the
                      table."
        ::= { filterProtocolEntry 4 }

-- the filter test table

filterTestTable OBJECT-TYPE
        SYNTAX        SEQUENCE OF FilterTestEntry
        MAX-ACCESS    not-accessible
        STATUS        current
        DESCRIPTION   "A list of filter test entries."
        ::= { filterGrp 4 }

filterTestEntry OBJECT-TYPE
        SYNTAX        FilterTestEntry
        MAX-ACCESS    not-accessible
        STATUS        current
        DESCRIPTION   "Entry containing test filter information."
        INDEX         { filterTestModule, filterTestPort,
                        filterTestIndex }
        ::= { filterTestTable 1 }

FilterTestEntry ::=
        SEQUENCE {
                filterTestModule
                        INTEGER,
                filterTestPort
                        INTEGER,
                filterTestIndex
                        INTEGER,
                filterTestType
                        INTEGER,
                filterTestOffset
                        INTEGER,
                filterTestValue
                        INTEGER,
                filterTestMask
                        INTEGER
        }

filterTestModule OBJECT-TYPE
        SYNTAX        INTEGER (1..16)
        MAX-ACCESS    read-only
        STATUS        current
        DESCRIPTION   "An index value that uniquely identifies the
                      module where this port is located
                      (see portModuleIndex)."
        ::= { filterTestEntry 1 }

filterTestPort OBJECT-TYPE
        SYNTAX        INTEGER (1..255)
        MAX-ACCESS    read-only
        STATUS        current
        DESCRIPTION   "An index value that uniquely identifies this port
                      within a module (see portIndex)."
        ::= { filterTestEntry 2 }

filterTestIndex OBJECT-TYPE
        SYNTAX        INTEGER (1..8)
        MAX-ACCESS    read-only
        STATUS        current
        DESCRIPTION   "An index value that uniquely identifies a test
                       for a particular module/port."
        ::= { filterTestEntry 3 }

filterTestType OBJECT-TYPE
        SYNTAX        INTEGER {
                                valid(1),        -- add this entry
                                invalid(2)       -- remove this entry
                                }
        MAX-ACCESS    read-create
        STATUS        current
        DESCRIPTION   "Setting this object to invalid(2) removes the
                      corresponding entry from the filterTestTable. To
                      add a new entry to the filterTestTable, set this
                      object to valid(1) for a module, port, and test
                      index not already in the table."
        ::= { filterTestEntry 4 }

filterTestOffset OBJECT-TYPE
        SYNTAX        INTEGER (0..4500)
        MAX-ACCESS    read-create
        STATUS        current
        DESCRIPTION   "A byte offset into packet. Must be a 32-bit word
                      aligned offset, i.e. 0, 4, 8, etc."
        ::= { filterTestEntry 5 }

filterTestValue OBJECT-TYPE
        SYNTAX        INTEGER (0..2147483647)
        MAX-ACCESS    read-create
        STATUS        current
        DESCRIPTION   "A 32-bit value to be compared against the packet
                      location specified by filterTestOffset."
        ::= { filterTestEntry 6 }

filterTestMask OBJECT-TYPE
        SYNTAX        INTEGER (0..2147483647)
        MAX-ACCESS    read-create
        STATUS        current
        DESCRIPTION   "A 32-bit value to be bitwise ANDed with the
                      packet location specified by filterTestOffset
                      before  being compared to filterTestValue."
        ::= { filterTestEntry 7 }

-- the filter port table

filterPortTable OBJECT-TYPE
        SYNTAX        SEQUENCE OF FilterPortEntry
        MAX-ACCESS    not-accessible
        STATUS        current
        DESCRIPTION   "A list of filter port entries. The number of
                      entries is determined by the number of modules in
                      the chassis and the number of ports on each
                      module."
        ::= { filterGrp 5 }

filterPortEntry OBJECT-TYPE
        SYNTAX        FilterPortEntry
        MAX-ACCESS    not-accessible
        STATUS        current
        DESCRIPTION   "Entry containing filter information for a
                      particular port on a module."
        INDEX         { filterPortModule, filterPort }
        ::= { filterPortTable 1 }

FilterPortEntry ::=
        SEQUENCE {
                filterPortModule
                        INTEGER,
                filterPort
                        INTEGER,
                filterPortComplex
                        DisplayString,
                filterPortBroadcastThrottle
                        INTEGER,
                filterPortBroadcastThreshold
                        INTEGER,
                filterPortBroadcastDiscards
                        Counter32,
                filterPortBroadcastThresholdFraction
                        INTEGER,
                filterPortSuppressionOption
                        BITS,
                filterPortSuppressionViolation
                        INTEGER
        }

filterPortModule OBJECT-TYPE
        SYNTAX        INTEGER (1..16)
        MAX-ACCESS    read-only
        STATUS        current
        DESCRIPTION   "An index value that uniquely identifies the
                      module where this port is located
                      (see portModuleIndex)."
        ::= { filterPortEntry 1 }

filterPort OBJECT-TYPE
        SYNTAX        INTEGER (1..255)
        MAX-ACCESS    read-only
        STATUS        current
        DESCRIPTION   "An index value that uniquely identifies this port
                      within a module (see portIndex)."
        ::= { filterPortEntry 2 }

filterPortComplex OBJECT-TYPE
        SYNTAX        DisplayString (SIZE (0..50))
        MAX-ACCESS    read-write
        STATUS        current
        DESCRIPTION   "A complex expression made up of the numbers 1
                      through 8 indicating test results from
                      filterTestIndex and using logical operators '&'
                      (and), '|' (or), '!' (not), and parenthesis. For
                      example: ((1 & 2) | !3). If this complex filter
                      matches a packet, it is dropped."
        ::= { filterPortEntry 3 }

filterPortBroadcastThrottle OBJECT-TYPE
        SYNTAX        INTEGER (0..150000)
        MAX-ACCESS    read-write
        STATUS        current
        DESCRIPTION   "The maximum number of broadcast packets per
                      second allowed on this port. If the number of
                      incoming broadcast packets in a one second
                      interval exceeds this amount, packets are
                      dropped for the rest of the interval. If the
                      capability exists, only broadcast packets should
                      be dropped. Otherwise, all packets are dropped
                      during the suppression interval.

                      A value of 0 indicates broadcast packets should
                      not be limited.

                      The ability to suppress broadcast packets in this
                      manner exists only on certain ports. If it does
                      not exist on this port, attempts to write a value
                      other than 0 are rejected.

                      This object also applies to multicast (and/or)
                      unicast suppression when
                      filterPortSuppressionOption is enabled."
        DEFVAL { 0 }
        ::= { filterPortEntry 4 }

filterPortBroadcastThreshold OBJECT-TYPE
        SYNTAX        INTEGER (0..100)
        MAX-ACCESS    read-write
        STATUS        current
        DESCRIPTION   "Indicates the integer part of the maximum
                      percentage of available bandwidth allowed for
                      incoming traffic of the specific traffic types on
                      this port. The associated object
                      filterPortBroadcastThresholdFraction indicates the
                      fraction part of the maximum percentage of
                      available bandwidth allowed for incoming traffic
                      of the specific traffic types on this port. Either
                      packets of the specific traffic types are dropped
                      of the port is put into errdisable state depending
                      on the value of filterPortSuppressionViolation on
                      this port if the percentage of incoming traffic of
                      the specific traffic types would exceed this
                      limit. The traffic types that are enabled for
                      this traffic suppression feature is indicated by
                      filterPortBroadcastOption.

                      The maximum percentage for the combination of this
                      object value and the object value of
                      filterPortBroadcastThresholdFraction is 100.00
                      which indicates traffic of all traffic types
                      should not be limited.

                      The ability to suppress traffic in this manner
                      exists only on certain ports. If it does not
                      exist on this port, attempts to write a value of
                      this object other than 100 are rejected.

                      On platforms where filterPortSuppressionOption
                      object is not supported, this object only applies
                      to broadcast suppression."
        DEFVAL { 100 }
        ::= { filterPortEntry 5 }

filterPortBroadcastDiscards OBJECT-TYPE
        SYNTAX        Counter32
        MAX-ACCESS    read-only
        STATUS        current
        DESCRIPTION   "The number of packets discarded due to traffic
                      suppression on this port."
        ::= { filterPortEntry 6 }

filterPortBroadcastThresholdFraction OBJECT-TYPE
        SYNTAX        INTEGER (0..99)
        UNITS         "one-hundredths"
        MAX-ACCESS    read-write
        STATUS        current
        DESCRIPTION   "Indicates the fraction part of the maximum
                      percentage of available bandwidth allowed for
                      incoming traffic of the specific traffic types on
                      this port. The associated object
                      filterPortBroadcastThreshold indicates the integer
                      part of the maximum percentage of available
                      bandwidth allowed for incoming traffic of the
                      specific traffic types on this port. Either
                      packets of the specific traffic types are dropped
                      or the port is put into errdisable state
                      depending on the value of
                      filterPortSuppressionViolation on this port if the
                      percentage of incoming traffic of the specific
                      traffic type would exceed this limit. The
                      traffic types that are enabled for this traffic
                      suppression feature is indicated by
                      filterPortBroadcastOption.

                      The maximum percentage for the combination
                      of this object value and the object value of
                      filterPortBroadcastThreshold is 100.00 which
                      indicates traffic of all traffic types should not
                      be limited.

                      The ability to suppress traffic in this manner
                      exists only on certain ports. If it does not exist
                      on this port, attempts to write a value of this
                      object other than 100 are rejected.

                      On platforms where filterPortSuppressionOption
                      object is not supported, this object only applies
                      to broadcast suppression."
        DEFVAL { 0 }
        ::= { filterPortEntry 7 }

filterPortSuppressionOption OBJECT-TYPE
--      SYNTAX        OCTET STRING
        SYNTAX        BITS {
                              multicast(0),
                              unicast(1),
                              broadcast(2)
                           }
        MAX-ACCESS    read-write
        STATUS        current
        DESCRIPTION   "Indicates the traffic types that traffic
                      suppression feature is enabled for.

                      multicast(0) is set when multicast suppression is
                      enabled. unicast(1) is set when unicast
                      suppression is enabled. broadcast(2) is set when
                      broadcast suppression is enabled."
        ::= { filterPortEntry 8 }

filterPortSuppressionViolation OBJECT-TYPE
        SYNTAX        INTEGER {
                              dropPackets(1),
                              errdisable(2)
                           }
        MAX-ACCESS    read-write
        STATUS        current
        DESCRIPTION   "Indicates the action that will be taken on this
                      port when the percentage of either broadcast,
                      multicast or unicast traffic exceeds the limit as
                      indicated by filterPortBroadcastThreshold and
                      filterPortBroadcastThresholdFraction.


                      dropPackets - the excessive packets will be
                                  - dropped on this port.

                      errdisable - the port will be put into errdisable
                                 - state.

                      The object is only supported on platforms that
                      support this suppression violation action
                      feature."
        ::= { filterPortEntry 9 }


-- the monitor group

-- Implementation of the monitor group is current for all Cisco
-- Workgroup Stack products which implement port monitoring functions.
--
-- The monitorGrp is deprecated and replaced by
-- portCopyTable defined in SMON-MIB.

monitorSourceModule OBJECT-TYPE
        SYNTAX        INTEGER (0..16)
        MAX-ACCESS    read-write
        STATUS        deprecated
        DESCRIPTION   "An index value that uniquely identifies the
                      module where the monitoring source port is
                      located. A value of 0 indicates that the
                      monitorSourcePort is really a source Virtual LAN
                      number. To monitor multiple source ports, this
                      object should be set to 0 and
                      monitorAdminSourcePorts should be configured."
        ::= { monitorGrp 1 }

monitorSourcePort OBJECT-TYPE
        SYNTAX        INTEGER (0..1023)
        MAX-ACCESS    read-write
        STATUS        deprecated
        DESCRIPTION   "An index value that uniquely identifies the
                      monitoring source port within a module or the
                      monitoring source Virtual LAN. To monitor multiple
                      source ports, this object should be set to 0 and
                      monitorAdminSourcePorts should be configured"
        ::= { monitorGrp 2 }

monitorDestinationModule OBJECT-TYPE
        SYNTAX        INTEGER (1..16)
        MAX-ACCESS    read-write
        STATUS        deprecated
        DESCRIPTION   "An index value that uniquely identifies the
                      module where the monitoring destination port is
                      located."
        ::= { monitorGrp 3 }

monitorDestinationPort OBJECT-TYPE
        SYNTAX        INTEGER (1..255)
        MAX-ACCESS    read-write
        STATUS        deprecated
        DESCRIPTION   "An index value that uniquely identifies the
                      monitoring destination port within a module."
        ::= { monitorGrp 4 }

monitorDirection OBJECT-TYPE
        SYNTAX        INTEGER {
                                transmit(1),
                                receive(2),
                                transmitAndReceive(3)
                              }
        MAX-ACCESS    read-write
        STATUS        deprecated
        DESCRIPTION   "The type of packets to be monitored at the source
                      port."
        DEFVAL { transmitAndReceive }
        ::= { monitorGrp 5 }

monitorEnable OBJECT-TYPE
        SYNTAX        INTEGER { enabled(1), disabled(2) }
        MAX-ACCESS    read-write
        STATUS        deprecated
        DESCRIPTION   "Indicates whether port monitoring is in
                      progress."
        DEFVAL { disabled }
        ::= { monitorGrp 6 }

monitorAdminSourcePorts OBJECT-TYPE
        SYNTAX        OCTET STRING (SIZE (0..128))
        MAX-ACCESS    read-write
        STATUS        deprecated
        DESCRIPTION   "Indicates the administrative status of which
                      ports are monitored. All the monitored ports have
                      to be non-trunking port and belong to the same
                      Virtual LAN. The octet string contains one bit
                      per port. Each bit within the octet string
                      represents one port of the device. The ordering
                      of ports represented within the octet string is
                      in the same order as in the RFC 1493
                      dot1dStpPortTable.

                      The bit value interpretation is as follows:
                              1 = being monitored
                              0 = not being monitored"
        ::= { monitorGrp 7 }


monitorOperSourcePorts OBJECT-TYPE
        SYNTAX        OCTET STRING  (SIZE (0..128))
        MAX-ACCESS    read-only
        STATUS        deprecated
        DESCRIPTION   "Indicates which ports are actually being
                      monitored. All the monitored ports have to be
                      non-trunking port and belong to the same Virtual
                      LAN. The octet string contains one bit per port.
                      Each bit within the octet string represents one
                      port of the device. The ordering of ports
                      represented within the octet string is in the same
                      order as in the RFC 1493 dot1dStpPortTable.

                      The bit value interpretation is as follows:
                              1 = being monitored
                              0 = not being monitored"
        ::= { monitorGrp 8 }



-- the VLAN group

-- the vlan table

vlanTable OBJECT-TYPE
        SYNTAX        SEQUENCE OF VlanEntry
        MAX-ACCESS    not-accessible
        STATUS        deprecated
        DESCRIPTION   "A list of Virtual LAN entries. The number of
                      entries is determined by the number of VLANs
                      supported by the system."
        ::= { vlanGrp 2 }

vlanEntry OBJECT-TYPE
        SYNTAX        VlanEntry
        MAX-ACCESS    not-accessible
        STATUS        deprecated
        DESCRIPTION   "Entry containing information for a particular
                      Virtual LAN."
        INDEX         { vlanIndex }
        ::= { vlanTable 1 }

VlanEntry ::=
        SEQUENCE {
                vlanIndex
                        VlanIndex,
                vlanSpantreeEnable
                        INTEGER,
                vlanIfIndex
                        INTEGER
        }

vlanIndex OBJECT-TYPE
        SYNTAX        VlanIndex
        MAX-ACCESS    read-only
        STATUS        deprecated
        DESCRIPTION   "An index value that uniquely identifies the
                      Virtual LAN associated with this information."
        ::= { vlanEntry 1 }

vlanSpantreeEnable OBJECT-TYPE
        SYNTAX        INTEGER { enabled(1), disabled(2),
                                notApplicable(3) }
        MAX-ACCESS    read-write
        STATUS        deprecated
        DESCRIPTION   "Indicates whether Spanning Tree protocol is
                      enabled for this Virtual LAN.

                      If the device only supports a single global
                      Spanning Tree PVST+ Protocol enable/disable
                      for all the existing VLANs, then the object
                      value assigned to this VLAN will be applied
                      to the object values of all the instances
                      in this table which do not have the value
                      of notApplicable(3).

                      This object is deprecated and replaced by
                      stpxPVSTVlanEnable in
                      CISCO-STP-EXTENSIONS-MIB."
        DEFVAL { enabled }
        ::= { vlanEntry 2 }

vlanIfIndex OBJECT-TYPE
        SYNTAX        INTEGER (1..2147483647)
        MAX-ACCESS    read-only
        STATUS        deprecated
        DESCRIPTION   "The value of the ifIndex object defined in
                      MIB-II, for the interface corresponding to this
                      VLAN.

                      This object is deprecated and replaced by
                      vtpVlanIfIndex in CISCO-VTP-MIB."
        ::= { vlanEntry 3 }

-- the vlan port table

vlanPortTable OBJECT-TYPE
        SYNTAX        SEQUENCE OF VlanPortEntry
        MAX-ACCESS    not-accessible
        STATUS        current
        DESCRIPTION   "A list of Virtual LAN port entries. The number of
                      entries is determined by the number of modules in
                      the chassis and the number of ports on each
                      module."
        ::= { vlanGrp 3 }

vlanPortEntry OBJECT-TYPE
        SYNTAX        VlanPortEntry
        MAX-ACCESS    not-accessible
        STATUS        current
        DESCRIPTION   "Entry containing Virtual LAN information for a
                      particular port on a module."
        INDEX         { vlanPortModule, vlanPort }
        ::= { vlanPortTable 1 }

VlanPortEntry ::=
        SEQUENCE {
                vlanPortModule
                        INTEGER,
                vlanPort
                        INTEGER,
                vlanPortVlan
                        VlanIndex,
                vlanPortIslVlansAllowed
                        OCTET STRING,
                vlanPortSwitchLevel
                        INTEGER,
                vlanPortIslAdminStatus
                        INTEGER,
                vlanPortIslOperStatus
                        INTEGER,
                vlanPortIslPriorityVlans
                        OCTET STRING,
                vlanPortAdminStatus
                        INTEGER,
                vlanPortOperStatus
                        INTEGER,
                vlanPortAuxiliaryVlan
                        INTEGER
        }

vlanPortModule OBJECT-TYPE
        SYNTAX        INTEGER (1..16)
        MAX-ACCESS    read-only
        STATUS        current
        DESCRIPTION   "An index value that uniquely identifies the
                      module where this port is located
                      (see portModuleIndex)."
        ::= { vlanPortEntry 1 }

vlanPort OBJECT-TYPE
        SYNTAX        INTEGER (1..255)
        MAX-ACCESS    read-only
        STATUS        current
        DESCRIPTION   "An index value that uniquely identifies this port
                      within a module (see portIndex)."
        ::= { vlanPortEntry 2 }

vlanPortVlan OBJECT-TYPE
        SYNTAX        VlanIndex
        MAX-ACCESS    read-write
        STATUS        current
        DESCRIPTION   "The Virtual LAN to which this port belongs."
        ::= { vlanPortEntry 3 }

-- vlanPortEntry 4 is not used

vlanPortIslVlansAllowed OBJECT-TYPE
        SYNTAX        OCTET STRING (SIZE (0..128))
        MAX-ACCESS    read-write
        STATUS        current
        DESCRIPTION   "An indication of which Virtual LANs are allowed
                      on this Inter-Switch Link. This is an octet string
                      value with bits set to indicate allowed VLANs. It
                      can be interpreted as a sum of f(x) as x goes from
                      0 to 1023, where f(x) = 0 for VLAN x not allowed
                      and f(x) = exp(2, x) for VLAN x allowed."
        ::= { vlanPortEntry 5 }

vlanPortSwitchLevel OBJECT-TYPE
        SYNTAX        INTEGER { normal(1), high(2), notApplicable(3) }
        MAX-ACCESS    read-write
        STATUS        current
        DESCRIPTION   "Indicates the priority level the port uses to
                      access the switching media. If vlanPortSwitchLevel
                      is not applicable to the port, notApplicable(3)
                      will be returned by the device."
        DEFVAL { normal }
        ::= { vlanPortEntry 6 }

vlanPortIslAdminStatus OBJECT-TYPE
        SYNTAX        INTEGER { on(1), off(2), desirable(3), auto(4),
                                onNoNegotiate(5) }
        MAX-ACCESS    read-write
        STATUS        current
        DESCRIPTION   "Indicates the administrative status set on the
                      trunk port while the operational status is the one
                      that indicates whether the port is actually
                      trunking or not. If the status is set to off(2),
                      the port is permanently set to be a non-trunk. If
                      the status is set to onNoNegotiate(5), the port is
                      permanently set to be a trunk and no negotiation
                      takes place with the far end to try to ensure
                      consistent operation. If the status is set to
                      on(1), the port initiates a request to become a
                      trunk and will become a trunk regardless of the
                      response from the far end. If the status is set to
                      desirable(3), the port initiates a request to
                      become a trunk and will become a trunk if the far
                      end agrees. If the status is set to auto(4), the
                      port does not initiate a request to become a trunk
                      but will do so if it receives a request to become
                      a trunk from the far end."
        ::= { vlanPortEntry 7 }

vlanPortIslOperStatus OBJECT-TYPE
        SYNTAX        INTEGER { trunking(1), notTrunking(2) }
        MAX-ACCESS    read-only
        STATUS        current
        DESCRIPTION   "Indicates if the port is actually trunking or
                      not. In the case of ISL capable ports, the status
                      depends on the success or failure of the
                      negotiation process initiated by the port to
                      become a trunk or non trunk.
                      In the case of 802.10 capable ports, it is
                      directly related to the on/off administrative
                      status."
        ::= { vlanPortEntry 8 }

vlanPortIslPriorityVlans OBJECT-TYPE
        SYNTAX        OCTET STRING (SIZE (0..128))
        MAX-ACCESS    read-write
        STATUS        current
        DESCRIPTION   "An indication of which Virtual LANs have a better
                      dot1dStpPortPriority value. This object can be
                      used to perform load balancing on Inter-Switch
                      Links via spanning tree. An Inter-Switch Link has
                      two dot1dStpPortPriority values which are shared
                      by all the Virtual LANs on the link. The Virtual
                      LANs indicated by this object have priority
                      over the other Virtual LANs on the link.

                      This is an octet string value with bits set to
                      indicate priority VLANs. It can be interpreted as
                      a sum of f(x) as x goes from 0 to 1023, where
                      f(x) = 0 for a VLAN x which does not have priority
                      and f(x) = exp(2, x) for a VLAN x which has
                      priority.

                      Setting the dot1dStpPortPriority value for any of
                      the Virtual LANs indicated by this object causes
                      the dot1dStpPortPriority value for all the Virtual
                      LANs indicated by this object to be set to the
                      same value.

                      Setting the dot1dStpPortPriority value for any
                      other Virtual LAN causes the dot1dStpPortPriority
                      value for all other Virtual LANs to be set to the
                      same value."
        ::= { vlanPortEntry 9 }

vlanPortAdminStatus OBJECT-TYPE
        SYNTAX        INTEGER { static(1), dynamic(2) }
        MAX-ACCESS    read-write
        STATUS        current
        DESCRIPTION   "Indicates whether the port will get assigned to a
                      VLAN statically or dynamically. When it is set to
                      dynamic, the needed information will be accessed
                      from one of the Vlan Membership Policy Servers
                      specified in the vmpsTable. Default value is
                      static(1).
                      Note that vlanPortAdminStatus cannot be set to
                      dynamic(2) for a port which has
                      portSecurityAdminStatus set to enabled(1) or for a
                      port which currently has a vlanPortIslOperStatus
                      of trunking(1)."
        DEFVAL { static }
        ::= { vlanPortEntry 10 }

vlanPortOperStatus OBJECT-TYPE
        SYNTAX        INTEGER { inactive(1),
                                active(2),
                                shutdown(3),
                                vlanActiveFault(4) }
        MAX-ACCESS    read-only
        STATUS        current
        DESCRIPTION   "An indication of the current VLAN status of the
                      port.
                      A status of inactive(1) indicates that a dynamic
                      port does not yet have a VLAN assigned or that a
                      static or dynamic port has been assigned a VLAN
                      that is not currently active. A status of
                      active(2) indicates that the currently assigned
                      VLAN is active. A status of shutdown(3) indicates
                      that the port has been shutdown as a result of a
                      VMPS response on a dynamic port.
                      A status of vlanActiveFault(4) only applies to
                      tokenring ports and indicates that the port is
                      operationally disabled because the TR-CRF VLAN of
                      which the port is a member has active ports on
                      another device and only ports on that remote
                      device may participate in that TR-CRF VLAN."
        ::= { vlanPortEntry 11 }

vlanPortAuxiliaryVlan OBJECT-TYPE
        SYNTAX        INTEGER ( 0|1..1000|1025..4094|4095|4096 )
        MAX-ACCESS    read-write
        STATUS        deprecated
        DESCRIPTION   "The Voice Virtual Vlan ID (VVID) to which this
                      port belongs to.
                      If the VVID is not supported on the port, this MIB
                      object will not be configurable and will return
                      4096.

                      Setting this MIB object to 4096, the CDP packets
                      transmitting through this port would not include
                      Appliance VLAN-ID TLV.

                      Setting this MIB object to 4095, the CDP packets
                      transmitting through this port would contain
                      Appliance VLAN-ID TLV with value of 4095 - VoIP
                      and related packets are expected to be sent and
                      received untagged without an 802.1p priority.

                      Setting this MIB object to 0, the CDP packets
                      transmitting through this port would contain
                      Appliance VLAN-ID TLV with value of 0 - VoIP
                      and related packets are expected to be sent and
                      received with VLAN-id=0 and an 802.1p priority.

                      Setting this MIB object to N (1..1000|1025..4094),
                      the CDP packets transmitting through this port
                      would contain Appliance VLAN-ID TLV with N - VoIP
                      and related packets are expected to be sent and
                      received with VLAN-id=N and an 802.1p priority.

                      This object is deprecated and replaced by
                      vmVoiceVlanId in CISCO-VLAN-MEMBERSHIP-MIB."
        ::= { vlanPortEntry 12 }

-- the Vlan Membership Policy Server table

vmpsTable OBJECT-TYPE
        SYNTAX        SEQUENCE OF VmpsEntry
        MAX-ACCESS    not-accessible
        STATUS        current
        DESCRIPTION   "This table lists a maximum of 3 IP addresses of
                      Vlan Membership Policy Servers."
        ::= { vlanGrp 4 }

vmpsEntry OBJECT-TYPE
        SYNTAX        VmpsEntry
        MAX-ACCESS    not-accessible
        STATUS        current
        DESCRIPTION   "A VMPS table entry."
        INDEX         { vmpsAddr }
        ::= { vmpsTable 1 }

VmpsEntry ::=
        SEQUENCE {
                vmpsAddr
                        IpAddress,
                vmpsType
                        INTEGER
        }

vmpsAddr OBJECT-TYPE
        SYNTAX        IpAddress
        MAX-ACCESS    read-only
        STATUS        current
        DESCRIPTION   "The IP address of a Vlan Membership Policy
                      Server. To configure the internal VMPS, use the
                      same IP address as specified in sysIpAddr."
        ::= { vmpsEntry 1 }

vmpsType OBJECT-TYPE
        SYNTAX        INTEGER {
                                invalid(1),   -- remove this entry
                                primary(2),   -- the primary entry
                                other(3)      -- a lower priority entry
                                }
        MAX-ACCESS    read-create
        STATUS        current
        DESCRIPTION   "To add a new entry to the vmpsTable, set this
                      object to primary(2) or other(3) for an IP address
                      which is not already in the table. The primary
                      entry will be used first, if it is reachable.
                      Otherwise one of the other entries will be used.
                      Setting one entry to primary(2) causes any
                      previous primary entry to change to other(3).
                      To remove an entry from the table, set this
                      object to invalid(1)."
        ::= { vmpsEntry 2 }

vmpsAction OBJECT-TYPE
        SYNTAX        INTEGER {
                  other(1),           -- none of following (read-only)
                  inProgress(2),      -- (read-only)
                  success(3),         -- (read-only)
                  noResponse(4),      -- (read-only)
                  noPrimaryVmps(5),   -- No VMPS configured (read-only)
                  noDynamicPort(6),   -- No dynamic ports configured
                                      -- (read-only)
                  noHostConnected(7), -- No hosts on dynamic ports
                                      -- (read-only)
                  reconfirm(8)        -- (write-only)
                              }
        MAX-ACCESS    read-write
        STATUS        current
        DESCRIPTION   "This object, when read, returns the result of the
                      last action requested: other(1), inProgress(2),
                      success(3), noResponse(3), noPrimaryVmps(5),
                      noDynamicPort(6), or noHostConnected(7).

                      Setting this object to reconfirm(8) causes the
                      switch to contact the Vlan Membership Policy
                      Server immediately to reconfirm the current VLAN
                      assignments for all dynamic ports on the switch.
                      Normally VLAN assignments for dynamic ports are
                      reconfirmed once an hour."
        ::= { vlanGrp 5 }

vmpsAccessed OBJECT-TYPE
        SYNTAX        IpAddress
        MAX-ACCESS    read-only
        STATUS        current
        DESCRIPTION   "The IP address of the last Vlan Membership Policy
                      Server accessed. If there was no response from the
                      last VMPS request, the value returned is 0."
        ::= { vlanGrp 6 }

-- trunk VLAN mapping table

vlanTrunkMappingMax OBJECT-TYPE
        SYNTAX        Unsigned32 (0..65535)
        UNITS         "entries"
        MAX-ACCESS    read-only
        STATUS        current
        DESCRIPTION   "Maximum number of active configurable trunk VLAN
                      mapping entries allowed. A value of zero indicates
                      no limitation on the number of active configurable
                      trunk VLAN mapping."
        ::= { vlanGrp 7 }

vlanTrunkMappingTable OBJECT-TYPE
        SYNTAX        SEQUENCE OF VlanTrunkMappingEntry
        MAX-ACCESS    not-accessible
        STATUS        current
        DESCRIPTION   "This table contains zero or more rows of trunk
                      VLAN to VLAN associations. The maximum number of
                      active entries is determined by
                      vlanTrunkMappingMax.

                      VLAN above 1k can not be created if the value of
                      corresponding instance of vlanTrunkMappingType is
                      dot1qToisl(2)."
        ::= { vlanGrp 8 }

vlanTrunkMappingEntry OBJECT-TYPE
        SYNTAX        VlanTrunkMappingEntry
        MAX-ACCESS    not-accessible
        STATUS        current
        DESCRIPTION   "Information about the VLAN mapping of a
                      particular trunk VLAN to another VLAN."
        INDEX         { vlanTrunkMappingFromVlan }
        ::= { vlanTrunkMappingTable 1 }

VlanTrunkMappingEntry ::=
        SEQUENCE {
                vlanTrunkMappingFromVlan  VlanIndex,
                vlanTrunkMappingToVlan    VlanIndex,
                vlanTrunkMappingType      INTEGER,
                vlanTrunkMappingOper      TruthValue,
                vlanTrunkMappingStatus    RowStatus
        }

vlanTrunkMappingFromVlan OBJECT-TYPE
        SYNTAX        VlanIndex
        MAX-ACCESS    not-accessible
        STATUS        current
        DESCRIPTION   "The VLAN with this VLAN ID will be mapped to the
                      VLAN in the corresponding instance of
                      vlanTrunkMappingToVlan in the device.

                      Agent returns inconsistentValue if this VLAN
                      exists in the device.

                      Agent returns inconsistentValue if this VLAN is
                      not a reserved VLAN and the value of corresponding
                      instance of vlanTrunkMappingType is
                      reservedToNonReserved(1).

                      Agent returns wrongValue if this VLAN is not a
                      valid 802.1Q VLAN and the value of corresponding
                      instance of vlanTrunkMappingType is
                      dot1qToisl(2)."
        ::= { vlanTrunkMappingEntry 1 }

vlanTrunkMappingToVlan OBJECT-TYPE
        SYNTAX        VlanIndex
        MAX-ACCESS    read-create
        STATUS        current
        DESCRIPTION   "The VLAN which the corresponding instance of
                      vlanTrunkMappingFromVlan will be mapped to.

                      Agent returns inconsistentValue if this VLAN
                      exists in the device.

                      Agent returns inconsistentValue if this VLAN is a
                      reserved VLAN and the value of corresponding
                      instance of vlanTrunkMappingType is
                      reservedToNonReserved(1).

                      Agent returns inconsistentValue if this VLAN is
                      not a valid ISL VLAN and the value of
                      corresponding instance of vlanTrunkMappingType
                      is dot1qToisl(2)."
        ::= { vlanTrunkMappingEntry 2 }

vlanTrunkMappingType OBJECT-TYPE
        SYNTAX        INTEGER {
                              reservedToNonReserved(1),
                              dot1qToisl(2)
                      }
        MAX-ACCESS    read-create
        STATUS        current
        DESCRIPTION   "The type of this trunk VLAN mapping.

                      reservedToNonReserved(1)
                          An user defined association which maps a
                          reserved VLAN to a non-reserved VLAN.

                      dot1qToisl(2)
                          An user defined association which maps a VLAN
                          in 802.1q trunk to a VLAN in ISL trunk.

                      Implementations are allowed to restrict the
                      available types for this object.

                      For devices which support the range of VlanIndex
                      between 1024 and 4095, the default value is
                      reservedToNonReserved(1).  The default value is
                      dot1qToisl(2) for devices which do not support the
                      range of VlanIndex between 1024 and 4095."
        ::= { vlanTrunkMappingEntry 3 }

vlanTrunkMappingOper OBJECT-TYPE
        SYNTAX        TruthValue
        MAX-ACCESS    read-only
        STATUS        current
        DESCRIPTION   "Indicates whether this VLAN mapping is effective
                      or not."
        ::= { vlanTrunkMappingEntry 4 }

vlanTrunkMappingStatus OBJECT-TYPE
        SYNTAX        RowStatus
        MAX-ACCESS    read-create
        STATUS        current
        DESCRIPTION   "The status of this trunk VLAN mapping.

                      Once a row becomes active, value in any other
                      column within such row cannot be modified except
                      by setting vlanTrunkMappingStatus to
                      notInService(2) for such row."
        ::= { vlanTrunkMappingEntry 5 }



-- the security group

-- Implementation of the security group is optional, but within the
-- group all the elements are current. If the Security feature is
-- implemented, the entire group should be implemented.

-- the port security table

portSecurityTable OBJECT-TYPE
        SYNTAX        SEQUENCE OF PortSecurityEntry
        MAX-ACCESS    not-accessible
        STATUS        current
        DESCRIPTION   "A list of port security entries. The number of
                      entries is determined by the number of ports in
                      the system which support the Security feature."
        ::= { securityGrp 1 }

portSecurityEntry OBJECT-TYPE
        SYNTAX        PortSecurityEntry
        MAX-ACCESS    not-accessible
        STATUS        current
        DESCRIPTION   "Entry containing security information for a
                      particular port."
        INDEX         { portSecurityModuleIndex, portSecurityPortIndex }
        ::= { portSecurityTable 1 }

PortSecurityEntry ::=
        SEQUENCE {
                portSecurityModuleIndex
                        INTEGER,
                portSecurityPortIndex
                        INTEGER,
                portSecurityAdminStatus
                        INTEGER,
                portSecurityOperStatus
                        INTEGER,
                portSecurityLastSrcAddr
                        OCTET STRING,
                portSecuritySecureSrcAddr
                        OCTET STRING,
                portSecurityMaxSrcAddr
                        INTEGER,
                portSecurityAgingTime
                        INTEGER,
                portSecurityShutdownTimeOut
                        INTEGER,
                portSecurityViolationPolicy
                        INTEGER
        }

portSecurityModuleIndex OBJECT-TYPE
        SYNTAX        INTEGER (1..16)
        MAX-ACCESS    read-only
        STATUS        current
        DESCRIPTION   "An index value that uniquely identifies the
                      module where this port is located
                      (see portModuleIndex)."
        ::= { portSecurityEntry 1 }

portSecurityPortIndex OBJECT-TYPE
        SYNTAX        INTEGER (1..255)
        MAX-ACCESS    read-only
        STATUS        current
        DESCRIPTION   "An index value that uniquely identifies this port
                      within a module (see portIndex)."
        ::= { portSecurityEntry 2 }

portSecurityAdminStatus OBJECT-TYPE
        SYNTAX        INTEGER { enabled(1),  disabled(2) }
        MAX-ACCESS    read-write
        STATUS        current
        DESCRIPTION   "When security is enabled, source MAC addresses
                      are monitored for all packets received on the
                      port. If an address is detected that does not
                      match the portSecuritySecureSrcAddr and any
                      corresponding portSecurityExtSecureSrcAddr, of
                      which portSecurityExtModuleIndex and
                      portSecurityExtPortIndex in the
                      portSecurityExtTable is the same as the
                      portSecurityModuleIndex and portSecurityPortIndex,
                      and the number of MAC address learned or
                      configured for this port is equal to
                      portSecurityMaxSrcAddr, the port will shutdown or
                      drop packets. If the
                      portSecurityViolationPolicy is set to shutdown(2),
                      the port is shutdown and a linkDown trap is sent;
                      otherwise the port drops the invalid packets."
        DEFVAL { disabled }
        ::= { portSecurityEntry 3 }

portSecurityOperStatus OBJECT-TYPE
        SYNTAX        INTEGER { notShutdown(1), shutdown(2) }
        MAX-ACCESS    read-only
        STATUS        current
        DESCRIPTION   "An indication of whether the port has been shut
                      down as a result of an insecure address being
                      detected on a secure port."
        ::= { portSecurityEntry 4 }

portSecurityLastSrcAddr OBJECT-TYPE
        SYNTAX        OCTET STRING (SIZE (6))
        MAX-ACCESS    read-only
        STATUS        current
        DESCRIPTION   "The last source MAC address in a receive packet
                      seen on the port."
        ::= { portSecurityEntry 5 }

portSecuritySecureSrcAddr OBJECT-TYPE
        SYNTAX        OCTET STRING (SIZE (6))
        MAX-ACCESS    read-write
        STATUS        current
        DESCRIPTION   "The address to be compared with source MAC
                      addresses of received packets when the
                      portSecurityAdminStatus is enabled(1). Setting
                      this value to 0.0.0.0.0.0 puts the port in
                      learning mode so that the next source MAC
                      address received by the port becomes the
                      portSecuritySecureSrcAddr."
        ::= { portSecurityEntry 6 }

portSecurityMaxSrcAddr OBJECT-TYPE
        SYNTAX        INTEGER(1..1025)
        MAX-ACCESS    read-write
        STATUS        current
        DESCRIPTION   "The maximum number (N) of MAC address to be
                      secured on the port. The first N MAC addresses
                      learned or configured are made secured. If the
                      user wants to make the port secured for more than
                      one MAC address, the portSecurityExtTable is used
                      in addition to portSecuritySecureSrcAddr. If
                      changing the maximum number N of Mac address to M,
                      which is smaller than N, some MAC addresses are
                      removed. Setting this value to 1,
                      the portSecurityExtTable will not be used for this
                      port and the corresponding entries for this port
                      will also be removed from portSecurityExtTable."
        DEFVAL { 1 }
        ::= { portSecurityEntry 7 }

portSecurityAgingTime OBJECT-TYPE
        SYNTAX        INTEGER(0|10..1440)
        UNITS         "minutes"
        MAX-ACCESS    read-write
        STATUS        current
        DESCRIPTION   "The interval in which the port is secured. After
                      the expiration of the time, the corresponding
                      portSecuritySecureSrcAddr or
                      portSecurityExtSecureSrcAddr will be removed from
                      the secure address list. If the value of this
                      object is 0, the aging mechanism is disabled."
        DEFVAL { 0 }
        ::= {portSecurityEntry 8}

portSecurityShutdownTimeOut OBJECT-TYPE
        SYNTAX        INTEGER(0|10..1440)
        UNITS         "minutes"
        MAX-ACCESS    read-write
        STATUS        current
        DESCRIPTION   "The interval in which the port is shutdown due to
                      the violation of security. After the expiration
                      of the time all the security configuration of this
                      port is re-installed and the port is enabled. If
                      the value of this object is 0, the port is shut
                      down permanently."
        DEFVAL { 0 }
        ::= {portSecurityEntry 9}

portSecurityViolationPolicy OBJECT-TYPE
        SYNTAX        INTEGER { restrict(1), shutdown(2)}
        MAX-ACCESS    read-write
        STATUS        current
        DESCRIPTION   "If the value of this object is
                        restrict(1)  - the port drops all packets with
                                       insecured addresses.
                        shutdown(2)  - the port is forced to shut down
                                       if there is a violation of
                                       security."
        DEFVAL { shutdown }
        ::= {portSecurityEntry 10}

-- the port security extension table. This table will be used if
-- the portSecurityMaxSrcAddr for any port is set to value that is
-- greater than 1.

portSecurityExtTable OBJECT-TYPE
        SYNTAX        SEQUENCE OF PortSecurityExtEntry
        MAX-ACCESS    not-accessible
        STATUS        current
        DESCRIPTION   "A list of port security entries. The number of
                      entries is determined by the number of ports in
                      the system which support the Security feature and
                      the number of MAC addresses learned/configured to
                      be secured per port."
        ::= { securityGrp 2 }

portSecurityExtEntry OBJECT-TYPE
        SYNTAX        PortSecurityExtEntry
        MAX-ACCESS    not-accessible
        STATUS        current
        DESCRIPTION   "Entry containing security information for a
                      particular port and a particular MAC address. The
                      entry can be configured by the user and can be
                      added by the agent when the device learns a new
                      secured MAC address."
        INDEX         { portSecurityExtModuleIndex,
                        portSecurityExtPortIndex,
                        portSecurityExtSecureSrcAddr }
        ::= { portSecurityExtTable 1 }

PortSecurityExtEntry ::=
        SEQUENCE {
                portSecurityExtModuleIndex
                        INTEGER,
                portSecurityExtPortIndex
                        INTEGER,
                portSecurityExtSecureSrcAddr
                        OCTET STRING,
                portSecurityExtControlStatus
                        INTEGER
                }
portSecurityExtModuleIndex OBJECT-TYPE
        SYNTAX        INTEGER (1..16)
        MAX-ACCESS    read-only
        STATUS        current
        DESCRIPTION   "An index value that uniquely identifies the
                      module where this port is located
                      (see portModuleIndex)."
        ::= { portSecurityExtEntry 1 }

portSecurityExtPortIndex OBJECT-TYPE
        SYNTAX        INTEGER (1..255)
        MAX-ACCESS    read-only
        STATUS        current
        DESCRIPTION   "An index value that uniquely identifies this port
                      within a module (see portIndex)."
        ::= { portSecurityExtEntry 2 }

portSecurityExtSecureSrcAddr OBJECT-TYPE
        SYNTAX        OCTET STRING (SIZE (6))
        MAX-ACCESS    read-only
        STATUS        current
        DESCRIPTION   "An index value that uniquely identifies the  MAC
                      address, which is to be secured."
        ::= { portSecurityExtEntry 3}

portSecurityExtControlStatus OBJECT-TYPE
        SYNTAX        INTEGER { valid(1), invalid(2)}
        MAX-ACCESS    read-create
        STATUS        current
        DESCRIPTION   "This object used to add or remove a secured
                      MAC address of the corresponding port in
                      the row. If setting this object to valid(1), the
                      portSecurityExtSecureSrcAddr is made to be secured
                      for the port. If setting this object to
                      invalid(2), the portSecurityExtSecureSrcAddr is
                      no longer to be secured for the current port."
        ::= {portSecurityExtEntry 4}



-- the token ring group

-- Implementation of the token ring group is current for all Cisco
-- Workgroup Stack products which implement token ring functions
-- (wsx5030 and wsx5031).

-- Token Ring Port Configuration Table

tokenRingPortTable OBJECT-TYPE
        SYNTAX        SEQUENCE OF TokenRingPortEntry
        MAX-ACCESS    not-accessible
        STATUS        current
        DESCRIPTION   "Table containing token ring configuration
                      information."
        ::= { tokenRingGrp 1 }

tokenRingPortEntry OBJECT-TYPE
        SYNTAX        TokenRingPortEntry
        MAX-ACCESS    not-accessible
        STATUS        current
        DESCRIPTION   "Entry containing token ring configuration
                      information for a particular port."
        INDEX         { tokenRingModuleIndex, tokenRingPortIndex }
        ::= { tokenRingPortTable 1 }

TokenRingPortEntry ::=
        SEQUENCE {
                tokenRingModuleIndex
                        INTEGER,
                tokenRingPortIndex
                        INTEGER,
                tokenRingPortSetACbits
                        INTEGER,
                tokenRingPortMode
                        INTEGER,
                tokenRingPortEarlyTokenRel
                        INTEGER,
                tokenRingPortPriorityThresh
                        INTEGER,
                tokenRingPortPriorityMinXmit
                        INTEGER,
                tokenRingPortCfgLossThresh
                        INTEGER,
                tokenRingPortCfgLossInterval
                        INTEGER
        }

tokenRingModuleIndex OBJECT-TYPE
        SYNTAX        INTEGER (1..16)
        MAX-ACCESS    read-only
        STATUS        current
        DESCRIPTION   "An index value that uniquely identifies the
                      module where this port is located
                      (see portModuleIndex)."
        ::= { tokenRingPortEntry 1 }

tokenRingPortIndex OBJECT-TYPE
        SYNTAX        INTEGER (1..255)
        MAX-ACCESS    read-only
        STATUS        current
        DESCRIPTION   "An index value that uniquely identifies this port
                      within a module (see portIndex)."
        ::= { tokenRingPortEntry 2 }

tokenRingPortSetACbits OBJECT-TYPE
        SYNTAX        INTEGER { enabled(1),  disabled(2) }
        MAX-ACCESS    read-write
        STATUS        current
        DESCRIPTION   "Specifies if the AC bits shall be set
                      unconditionally when a port forwards certain LLC
                      frames."
        DEFVAL { disabled }
        ::= { tokenRingPortEntry 3 }

tokenRingPortMode OBJECT-TYPE
        SYNTAX        INTEGER { auto(1),
                                fdxCport(2),
                                fdxStation(3),
                                hdxCport(4),
                                hdxStation(5),
                                riro(7) }
        MAX-ACCESS    read-write
        STATUS        current
        DESCRIPTION   "Specifies the port's mode of operation.

                      auto:       Automatically detect the port mode
                                  upon insertion.

                      fdxCport:   Transmit Immediate (full-duplex)
                                  Concentrator Port

                      fdxStation: Transmit Immediate (full-duplex)
                                  Station emulation

                      hdxCport:   Token Passing Protocol (half-duplex)
                                  Concentrator Port

                      hdxStation: Token Passing Protocol (half-duplex)
                                  Station emulation

                      riro:       RingIn/RingOut mode. (wsx5031 only)"
        DEFVAL { auto }
        ::= { tokenRingPortEntry 4 }

-- tokenRingPortEntry 5 to 8 are not used

tokenRingPortEarlyTokenRel OBJECT-TYPE
        SYNTAX        INTEGER { enabled(1),  disabled(2) }
        MAX-ACCESS    read-write
        STATUS        current
        DESCRIPTION   "This object provides the ability to enable or
                      disable early token release for a particular port.

                      Early token release only applies to ports
                      operating at 16 Mbps. If ifSpeed reflects 4 Mbps
                      for a particular port, then the corresponding
                      instance of this object will have a value of
                      disabled(2) regardless of attempts to set the
                      object to enabled(1).

                      Whenever a port is opened with a ring speed of
                      16 Mbps, by default, early token release will be
                      enabled."
        ::= { tokenRingPortEntry 9 }

tokenRingPortPriorityThresh OBJECT-TYPE
        SYNTAX        INTEGER (0..7)
        MAX-ACCESS    read-write
        STATUS        current
        DESCRIPTION   "The highest token ring frame priority that shall
                      go to the low-priority transmit queue."
        DEFVAL { 3 }
        ::= { tokenRingPortEntry 10 }

tokenRingPortPriorityMinXmit OBJECT-TYPE
        SYNTAX        INTEGER (0..6)
        MAX-ACCESS    read-write
        STATUS        current
        DESCRIPTION   "The minimum token priority that will be used for
                      transmit."
        DEFVAL { 4 }
        ::= { tokenRingPortEntry 11 }

tokenRingPortCfgLossThresh OBJECT-TYPE
        SYNTAX        INTEGER (1..100)
        MAX-ACCESS    read-write
        STATUS        current
        DESCRIPTION   "Number of configuration loss events during the
                      sample interval which, if exceeded, should cause
                      the port to be disabled. If the port is disabled
                      by this function the port must be administratively
                      re-enabled."
        DEFVAL { 8 }
        ::= { tokenRingPortEntry 12 }

tokenRingPortCfgLossInterval OBJECT-TYPE
        SYNTAX        INTEGER (1..9999)
        MAX-ACCESS    read-write
        STATUS        current
        DESCRIPTION   "The sampling interval, in minutes, for which the
                      port monitors to see if the configuration loss
                      threshold has been exceeded."
        DEFVAL { 10 }
        ::= { tokenRingPortEntry 13 }

-- DRiP related objects.
tokenRingDripDistCrfMode OBJECT-TYPE
         SYNTAX        INTEGER { enabled(1), disabled(2) }
        MAX-ACCESS    read-write
        STATUS        current
        DESCRIPTION   "This object reflects whether TR-CRFs can be
                      distributed across ISL topologies. Setting
                      this object to enabled(1) allows TR-CRFs to be
                      distributed. Setting this object to disabled(2)
                      prevents TR-CRFs from being distributed across
                      ISL topologies. When this object is set to
                      disabled(2), the system will disable ports
                      involved in the distributed TR-CRF."
        DEFVAL { disabled }
        ::= { tokenRingGrp 2 }

tokenRingDripAreReductionMode OBJECT-TYPE
        SYNTAX        INTEGER { enabled(1), disabled(2) }
        MAX-ACCESS    read-write
        STATUS        current
        DESCRIPTION   "This object reflects whether or not All
                      Routes Explorer (ARE) reduction capabilities are
                      enabled or disabled on this system. Setting
                      this object to enabled(1) will permit DRiP to
                      participate in the configuration of Token Ring
                      ports ARE reduction capabilities on the system.
                      Setting this object to disabled(2) will prevent
                      DRiP from participating in the configuration
                      of Token Ring port ARE reduction capabilities."
        DEFVAL { enabled }
        ::= { tokenRingGrp 3 }

tokenRingDripLocalNodeID OBJECT-TYPE
        SYNTAX        OCTET STRING (SIZE(6))
        MAX-ACCESS    read-only
        STATUS        current
        DESCRIPTION   "The unique system identifier that will be sent
                      in all advertisements generated by this system.
                      It uniquely identifies this system from other
                      DRiP capable systems."
        ::= { tokenRingGrp 4 }

tokenRingDripLastRevision OBJECT-TYPE
        SYNTAX        INTEGER (0..9999999)
        MAX-ACCESS    read-only
        STATUS        current
        DESCRIPTION   "The revision number transmitted in the most
                      recent advertisement. That advertisement may
                      or may not have contained changed data."
        ::= { tokenRingGrp 5 }

tokenRingDripLastChangedRevision OBJECT-TYPE
        SYNTAX        INTEGER (0..9999999)
        MAX-ACCESS    read-only
        STATUS        current
        DESCRIPTION   "The revision number transmitted in the most
                      recent advertisement containing changed data."
        ::= { tokenRingGrp 6 }

tokenRingDripAdvertsReceived OBJECT-TYPE
        SYNTAX        Counter32
        MAX-ACCESS    read-only
        STATUS        current
        DESCRIPTION   "The number of DRiP advertisements received
                      by this system."
        ::= { tokenRingGrp 7 }

tokenRingDripAdvertsTransmitted OBJECT-TYPE
        SYNTAX        Counter32
        MAX-ACCESS    read-only
        STATUS        current
        DESCRIPTION   "The number of DRiP advertisements transmitted
                      by this system."
        ::= { tokenRingGrp 8 }

tokenRingDripAdvertsProcessed OBJECT-TYPE
        SYNTAX        Counter32
        MAX-ACCESS    read-only
        STATUS        current
        DESCRIPTION   "The number of DRiP advertisements processed
                      by this system."
        ::= { tokenRingGrp 9 }

tokenRingDripInputQueueDrops OBJECT-TYPE
        SYNTAX        Counter32
        MAX-ACCESS    read-only
        STATUS        current
        DESCRIPTION   "The number of DRiP advertisements dropped
                      from this system's input queue."
        ::= { tokenRingGrp 10 }

tokenRingDripOutputQueueDrops OBJECT-TYPE
        SYNTAX        Counter32
        MAX-ACCESS    read-only
        STATUS        current
        DESCRIPTION   "The number of DRiP advertisements dropped
                      from this system's output queue."
        ::= { tokenRingGrp 11 }

tokenRingDripLocalVlanStatusTable OBJECT-TYPE
        SYNTAX        SEQUENCE OF TokenRingDripLocalVlanStatusEntry
        MAX-ACCESS    not-accessible
        STATUS        current
        DESCRIPTION   "A table containing DRiP VLAN status information
                      local to this system. The existence of an
                      entry indicates that at least one local port
                      is assigned to the associated TR-CRF VLAN."
        ::= { tokenRingGrp 12 }

tokenRingDripLocalVlanStatusEntry OBJECT-TYPE
        SYNTAX        TokenRingDripLocalVlanStatusEntry
        MAX-ACCESS    not-accessible
        STATUS        current
        DESCRIPTION   "Entry containing DRiP related information for
                      a particular TR-CRF VLAN."
        INDEX         { tokenRingDripVlan }
        ::= { tokenRingDripLocalVlanStatusTable 1 }

TokenRingDripLocalVlanStatusEntry ::=
        SEQUENCE {
                tokenRingDripVlan
                        VlanIndex,
                tokenRingDripLocalPortStatus
                        INTEGER,
                tokenRingDripRemotePortStatus
                        INTEGER,
                tokenRingDripRemotePortConfigured
                        INTEGER,
                tokenRingDripDistributedCrf
                        INTEGER,
                tokenRingDripBackupCrf
                        INTEGER,
                tokenRingDripOwnerNodeID
                        OCTET STRING
        }

tokenRingDripVlan OBJECT-TYPE
        SYNTAX        VlanIndex
        MAX-ACCESS    read-only
        STATUS        current
        DESCRIPTION   "A TR-CRF VLAN ID."
        ::= { tokenRingDripLocalVlanStatusEntry 1 }

tokenRingDripLocalPortStatus OBJECT-TYPE
        SYNTAX        INTEGER { active(1), inactive(2) }
        MAX-ACCESS    read-only
        STATUS        current
        DESCRIPTION   "This object reflects DRiP's status regarding
                      the overall set of local ports assigned to
                      the TR-CRF VLAN associated with this entry.
                      A value of active(1) indicates that at least
                      one local port is inserted/connected (i.e.,
                      active on the Token Ring). A value of inactive(2)
                      indicates that none of the local ports are
                      inserted/connected. All local ports are either
                      disabled or are simply not connected."
        ::= { tokenRingDripLocalVlanStatusEntry 2 }

tokenRingDripRemotePortStatus OBJECT-TYPE
        SYNTAX        INTEGER { active(1), inactive(2) }
        MAX-ACCESS    read-only
        STATUS        current
        DESCRIPTION   "This object reflects DRiP's status regarding
                      any ports on remote systems. A value of
                      active(1) indicates that at least one remote
                      port is inserted/connected (i.e., active on
                      the Token Ring). A value of inactive(2) indicates
                      that none of the remote ports are
                      inserted/connected. All remote ports are either
                      disabled or are simply not connected."
        ::= { tokenRingDripLocalVlanStatusEntry 3 }

tokenRingDripRemotePortConfigured OBJECT-TYPE
        SYNTAX        INTEGER { true(1), false(2) }
        MAX-ACCESS    read-only
        STATUS        current
        DESCRIPTION   "This object reflects whether or not DRiP has
                      detected remote ports assigned to the TR-CRF
                      VLAN associated with this entry. A value of
                      true(1) indicates there is at least one port
                      on a remote system assigned to this TR-CRF VLAN.
                      A value of false(2) indicates no remote ports
                      are assigned to this TR-CRF VLAN."
        ::= { tokenRingDripLocalVlanStatusEntry 4 }

tokenRingDripDistributedCrf OBJECT-TYPE
        SYNTAX        INTEGER { true(1), false(2) }
        MAX-ACCESS    read-only
        STATUS        current
        DESCRIPTION   "This object reflects whether DRiP considers the
                      TR-CRF VLAN associated with this entry to be
                      distributed across systems. A value of true(1)
                      indicates the TR-CRF is distributed. A value
                      of false(2) indicates the TR-CRF is not
                      distributed."
        ::= { tokenRingDripLocalVlanStatusEntry 5 }

tokenRingDripBackupCrf OBJECT-TYPE
        SYNTAX        INTEGER { true(1), false(2) }
        MAX-ACCESS    read-only
        STATUS        current
        DESCRIPTION   "This object reflects whether or not the TR-CRF
                      VLAN associated with this entry is configured
                      as a backup TR-CRF. A value of true(1) indicates
                      the TR-CRF is a configured as a backup. A value
                      of false(2) indicates the TR-CRF is not configured
                      as a backup."
        ::= { tokenRingDripLocalVlanStatusEntry 6 }

tokenRingDripOwnerNodeID OBJECT-TYPE
        SYNTAX        OCTET STRING (SIZE(6))
        MAX-ACCESS    read-only
        STATUS        current
        DESCRIPTION   "The unique identifier  of the system that has
                      advertised that it has local ports assigned to the
                      TR-CRF VLAN associated with this entry."
        ::= { tokenRingDripLocalVlanStatusEntry 7 }

-- Token Ring Port Soft Error Monitoring Configuration Table
tokenRingPortSoftErrTable OBJECT-TYPE
        SYNTAX        SEQUENCE OF TokenRingPortSoftErrEntry
        MAX-ACCESS        not-accessible
        STATUS        current
        DESCRIPTION   "Table containing token ring soft error monitoring
                       configuration information."
        ::= { tokenRingGrp 14 }
tokenRingPortSoftErrEntry OBJECT-TYPE
        SYNTAX        TokenRingPortSoftErrEntry
        MAX-ACCESS        not-accessible
        STATUS        current
        DESCRIPTION   "Entry containing token ring soft error monitoring
                       configuration information for a particular port."
        AUGMENTS      { tokenRingPortEntry }
       ::= { tokenRingPortSoftErrTable 1 }

TokenRingPortSoftErrEntry ::= SEQUENCE {
                        tokenRingPortSoftErrThresh
                                     INTEGER,
                        tokenRingPortSoftErrReportInterval
                                     INTEGER,
                        tokenRingPortSoftErrResetCounters
                                     INTEGER,
                        tokenRingPortSoftErrLastCounterReset
                                     TimeTicks,
                        tokenRingPortSoftErrEnable
                                     INTEGER
                        }
tokenRingPortSoftErrThresh OBJECT-TYPE
         SYNTAX       INTEGER ( 1..255 )
         MAX-ACCESS   read-write
         STATUS       current
         DESCRIPTION  "The number of soft errors reported from a station
                       connected to this port which, if exceeded, should
                      cause a soft error exceeded trap to be issued.
                      The error counters being monitored and compared to
                      this threshold value are all of the error counters
                      in the ringStationTable (see RFC 1513)."
         DEFVAL { 100 }
         ::= { tokenRingPortSoftErrEntry 1 }

tokenRingPortSoftErrReportInterval OBJECT-TYPE
         SYNTAX        INTEGER ( 0..65535 )
         MAX-ACCESS    read-write
         STATUS        current
         DESCRIPTION   "The sampling period, in seconds, in which each
                        station connected to this port will be monitored
                        for excessive soft error reports. If a station
                        reports more than tokenRingPortSoftErrThreshold
                        errors within the sampling period a trap will be
                        issued to the management station(s). Setting a
                        value of 0 will cause no traps to be sent for
                        this port."
         DEFVAL { 60 }
         ::= { tokenRingPortSoftErrEntry 2 }

tokenRingPortSoftErrResetCounters OBJECT-TYPE
         SYNTAX       INTEGER { noop(1), reset(2) }
         MAX-ACCESS   read-write
         STATUS       current
         DESCRIPTION  "When this object is set to reset(2), all Soft
                       Error Monitoring related counters on this port
                       will be set to 0."
         ::= { tokenRingPortSoftErrEntry 3 }

tokenRingPortSoftErrLastCounterReset OBJECT-TYPE
         SYNTAX       TimeTicks
         MAX-ACCESS   read-only
         STATUS       current
         DESCRIPTION  "The time (in hundredths of a second) since Soft
                       Error Monitoring counters for this port were last
                       cleared."
         ::= { tokenRingPortSoftErrEntry 4 }

tokenRingPortSoftErrEnable OBJECT-TYPE
        SYNTAX        INTEGER { enabled(1), disabled(2) }
        MAX-ACCESS    read-write
        STATUS        current
        DESCRIPTION  "Indicates whether the Token Ring Soft Error
                      Monitoring feature is enabled on this port or not.
                      The detailed soft error statistics are provided
                      by Token Ring RMON SNMP objects. Thus, if RMON
                      (sysEnableRmon) is disabled(2) then the soft error
                      statistics will only be available from the CLI."
         DEFVAL { disabled }
        ::= { tokenRingPortSoftErrEntry 5 }



-- the multicast group

-- Implementation of the multicast group is optional, but within the
-- group all the elements are current. If multicast features are
-- supported, the entire group should be implemented.

-- the multicast router table

mcastRouterTable OBJECT-TYPE
        SYNTAX        SEQUENCE OF McastRouterEntry
        MAX-ACCESS    not-accessible
        STATUS        current
        DESCRIPTION   "A list of multicast router port entries. The
                      number of entries is determined by the number of
                      ports in the system."
        ::= { multicastGrp 1 }

mcastRouterEntry OBJECT-TYPE
        SYNTAX        McastRouterEntry
        MAX-ACCESS    not-accessible
        STATUS        current
        DESCRIPTION   "Entry containing multicast router information for
                      a particular port."
        INDEX         { mcastRouterModuleIndex, mcastRouterPortIndex }
        ::= { mcastRouterTable 1 }

McastRouterEntry ::=
        SEQUENCE {
                mcastRouterModuleIndex
                        INTEGER,
                mcastRouterPortIndex
                        INTEGER,
                mcastRouterAdminStatus
                        INTEGER,
                mcastRouterOperStatus
                        INTEGER
        }

mcastRouterModuleIndex OBJECT-TYPE
        SYNTAX        INTEGER (1..16)
        MAX-ACCESS    read-only
        STATUS        current
        DESCRIPTION   "An index value that uniquely identifies the
                      module where this port is located
                      (see portModuleIndex)."
        ::= { mcastRouterEntry 1 }

mcastRouterPortIndex OBJECT-TYPE
        SYNTAX        INTEGER (1..255)
        MAX-ACCESS    read-only
        STATUS        current
        DESCRIPTION   "An index value that uniquely identifies this port
                      within a module (see portIndex)."
        ::= { mcastRouterEntry 2 }

mcastRouterAdminStatus OBJECT-TYPE
        SYNTAX        INTEGER { routerPresent(1),
                                dynamic(3) }
        MAX-ACCESS    read-write
        STATUS        current
        DESCRIPTION   "And indication of whether the presence of an IP
                      multicast router on this port is to be determined
                      statically or dynamically. The value
                      routerPresent(1) indicates that the presence of a
                      router is statically configured to be present.
                      The value dynamic(3) indicates the presence is to
                      be learned dynamically."
        DEFVAL { dynamic }
        ::= { mcastRouterEntry 3 }

mcastRouterOperStatus OBJECT-TYPE
        SYNTAX        INTEGER { routerPresent(1), noRouter(2) }
        MAX-ACCESS    read-only
        STATUS        current
        DESCRIPTION   "An indication of whether an IP multicast router
                      is present on this port."
        ::= { mcastRouterEntry 4 }

mcastEnableCgmp OBJECT-TYPE
        SYNTAX        INTEGER { enabled(1), disabled(2) }
        MAX-ACCESS    read-write
        STATUS        current
        DESCRIPTION   "Indicates whether Cisco Group Management Protocol
                      is enabled on the device or not. When CGMP is
                      enabled in conjunction with Cisco routers running
                      CGMP, only the required ports will participate in
                      IP multicast groups."
        DEFVAL { disabled }
        ::= { multicastGrp 2 }

mcastEnableIgmp OBJECT-TYPE
        SYNTAX        INTEGER { enabled(1), disabled(2) }
        MAX-ACCESS    read-write
        STATUS        current
        DESCRIPTION   "Indicates whether Internet Group Management
                      Protocol is enabled on the device or not. When
                      IGMP is enabled in conjunction with Cisco routers
                      running CGMP, only the required ports will
                      participate in IP multicast groups."
        DEFVAL { disabled }
        ::= { multicastGrp 3 }

mcastEnableRgmp OBJECT-TYPE
        SYNTAX        INTEGER {
                                enabled(1),
                                disabled(2)
                              }
        MAX-ACCESS    read-write
        STATUS        current
        DESCRIPTION   "Indicates whether Router Group Management
                      Protocol is enabled on the device or not. When
                      RGMP is enabled in conjunction with Cisco routers
                      running RGMP, multicast data traffic is forwarded
                      only to those multicast routers that are
                      interested to receive that data traffic. IGMP
                      snooping feature must be enabled on the system
                      to make RGMP feature operational."
        DEFVAL { disabled }
        ::= { multicastGrp 4 }



-- the DNS group

-- Implementation of the DNS group is optional, but within the group
-- all the elements are current. If DNS features are supported,
-- the entire group should be implemented.

dnsEnable OBJECT-TYPE
        SYNTAX        INTEGER { enabled(1), disabled(2) }
        MAX-ACCESS    read-write
        STATUS        current
        DESCRIPTION   "Indicates if the DNS feature is enabled or
                      disabled."
        DEFVAL { disabled }
        ::= { dnsGrp 1}

dnsServerTable OBJECT-TYPE
        SYNTAX        SEQUENCE OF DnsServerEntry
        MAX-ACCESS    not-accessible
        STATUS        current
        DESCRIPTION   "This table lists a maximum of 3 DNS servers."
        ::= { dnsGrp 2 }

dnsServerEntry OBJECT-TYPE
        SYNTAX        DnsServerEntry
        MAX-ACCESS    not-accessible
        STATUS        current
        DESCRIPTION   "A DNS server table entry."
        INDEX         { dnsServerAddr }
        ::= { dnsServerTable 1 }

DnsServerEntry ::=
        SEQUENCE {
                dnsServerAddr
                        IpAddress,
                dnsServerType
                        INTEGER
        }

dnsServerAddr OBJECT-TYPE
        SYNTAX        IpAddress
        MAX-ACCESS    read-only
        STATUS        current
        DESCRIPTION   "The IP address of a DNS server."
        ::= { dnsServerEntry 1 }

dnsServerType OBJECT-TYPE
        SYNTAX        INTEGER {
                                 invalid(1),   -- remove this entry
                                 primary(2),   -- the primary entry
                                 other(3)      -- a lower priority entry
                               }
        MAX-ACCESS    read-create
        STATUS        current
        DESCRIPTION   "To add a new entry to the dnsServerTable, set
                       this object to primary(2) or other(3) for an IP
                       address which is not already in the table. The
                       primary entry will be used first, if it is
                       reachable. Otherwise, one of the other entries
                       will be used. Setting one entry to primary(2)
                       causes any previous primary entry to change to
                       other(3). To remove an entry from the table, set
                       this object to invalid(1)."
         ::= { dnsServerEntry 2 }

dnsDomainName OBJECT-TYPE
        SYNTAX        DisplayString (SIZE (0..127))
        MAX-ACCESS    read-write
        STATUS        current
        DESCRIPTION   "DNS domain name."
        REFERENCE     "RFC1035, section 2.3.1 Preferred name syntax."
        ::= { dnsGrp 3 }



-- the syslog (System Log Information) group

-- Implementation of the syslog group is optional, but within the group
-- all the elements are current. If the syslog feature is supported,
-- the entire group should be implemented.


syslogServerTable OBJECT-TYPE
        SYNTAX        SEQUENCE OF SyslogServerEntry
        MAX-ACCESS    not-accessible
        STATUS        current
        DESCRIPTION   "This table lists a maximum of 3 system log
                      servers."
        ::= { syslogGrp 1 }

syslogServerEntry OBJECT-TYPE
        SYNTAX        SyslogServerEntry
        MAX-ACCESS    not-accessible
        STATUS        current
        DESCRIPTION   "A system log server table entry."
        INDEX         { syslogServerAddr }
        ::= { syslogServerTable 1 }

SyslogServerEntry ::=
        SEQUENCE {
                syslogServerAddr
                        IpAddress,
                syslogServerType
                        INTEGER
        }

syslogServerAddr OBJECT-TYPE
        SYNTAX        IpAddress
        MAX-ACCESS    read-only
        STATUS        current
        DESCRIPTION   "The IP address of a system log Server."
        ::= { syslogServerEntry 1 }

syslogServerType OBJECT-TYPE
        SYNTAX        INTEGER {
                                valid(1),   -- add this entry
                                invalid(2)  -- remove this entry
                              }
        MAX-ACCESS    read-create
        STATUS        current
        DESCRIPTION   "To add/remove a new entry to the
                      syslogServerTable, setting to invalid(2) removes
                      the corresponding entry from the
                      syslogServerTable. To add a new entry into
                      syslogServerTable, set this object to valid(1)
                      for an IP address which is not already in the
                      table."
        ::= { syslogServerEntry 2 }


syslogConsoleEnable OBJECT-TYPE
        SYNTAX        INTEGER { enabled(1), disabled(2) }
        MAX-ACCESS    read-write
        STATUS        current
        DESCRIPTION   "Indicate whether the system log messages should
                       be sent to console."
        DEFVAL { disabled }
        ::= { syslogGrp 2 }


syslogHostEnable OBJECT-TYPE
        SYNTAX        INTEGER { enabled(1), disabled(2) }
        MAX-ACCESS    read-write
        STATUS        current
        DESCRIPTION   "Indicate whether the system log messages should
                      be sent to syslog servers."
        DEFVAL { disabled }
        ::= { syslogGrp 3 }


syslogMessageControlTable OBJECT-TYPE
        SYNTAX        SEQUENCE OF SyslogMessageControlEntry
        MAX-ACCESS    not-accessible
        STATUS        current
        DESCRIPTION   "This table contains the information about what
                      system log messages should be sent to syslog host,
                      console, login session, and/or logged into the
                      internal buffer."
        ::= { syslogGrp 4 }

syslogMessageControlEntry OBJECT-TYPE
        SYNTAX        SyslogMessageControlEntry
        MAX-ACCESS    not-accessible
        STATUS        current
        DESCRIPTION   "A system log message control table entry."
        INDEX         { syslogMessageFacility }
        ::= { syslogMessageControlTable 1 }

SyslogMessageControlEntry ::=
        SEQUENCE {
                syslogMessageFacility
                        INTEGER,
                syslogMessageSeverity
                        INTEGER
        }

syslogMessageFacility OBJECT-TYPE
        SYNTAX        INTEGER {
                                cdp(1),
                                mcast(2),
                                dtp(3),
                                dvlan(4),
                                earl(5),
                                fddi(6),
                                ip(7),
                                pruning(8),
                                snmp(9),
                                spantree(10),
                                system(11),
                                tac(12),
                                tcp(13),
                                telnet(14),
                                tftp(15),
                                vtp(16),
                                vmps(17),
                                kernel(18),
                                filesys(19),
                                drip(20),
                                pagp(21),
                                mgmt(22),
                                mls(23),
                                protfilt(24),
                                security(25),
                                radius(26),
                                udld(27),
                                gvrp(28),
                                cops(29),
                                qos(30),
                                acl(31),
                                rsvp(32),
                                ld(33),
                                privatevlan(34),
                                ethc(35),
                                gl2pt(36),
                                callhome(37),
                                dhcpsnooping(38),
                                diags(40),
                                eou(42),
                                backup(43),
                                eoam(44),
                                webauth(45),
                                dom(46),
                                mvrp(47)
                              }
        MAX-ACCESS    read-only
        STATUS        current
        DESCRIPTION   "System log message facility."
        ::= { syslogMessageControlEntry 1 }


syslogMessageSeverity OBJECT-TYPE
        SYNTAX        INTEGER {
                                emergencies(1),
                                alerts(2),
                                critical(3),
                                errors(4),
                                warnings(5),
                                notification(6),
                                informational(7),
                                debugging(8)
                              }
        MAX-ACCESS    read-create
        STATUS        current
        DESCRIPTION   "System log message severity."
        ::= { syslogMessageControlEntry 2 }

syslogTimeStampOption OBJECT-TYPE
        SYNTAX        INTEGER{
                              enabled(1),
                              disabled(2)
                              }
        MAX-ACCESS    read-write
        STATUS        current
        DESCRIPTION   "Indicates whether syslog Time Stamp Option is
                      enabled or not. If it is set to enabled(1), the
                      Time Stamp will be in the beginning of each
                      syslog message."
        ::= { syslogGrp 5 }


syslogTelnetEnable OBJECT-TYPE
        SYNTAX        INTEGER { enabled(1), disabled(2) }
        MAX-ACCESS    read-write
        STATUS        current
        DESCRIPTION   "Indicate whether the system log messages should
                       be sent to telnet sessions."
        DEFVAL { enabled }
        ::= { syslogGrp 6 }


-- the NTP (Network Time Protocol) group

-- Implementation of the NTP group is optional, but within the group
-- all the elements are current. If the NTP feature is supported,
-- the entire group should be implemented.

-- the NTP table


ntpBcastClient OBJECT-TYPE
        SYNTAX        INTEGER { enabled(1),  disabled(2) }
        MAX-ACCESS    read-write
        STATUS        current
        DESCRIPTION   "Entry which tells if Cat5000 should act as a
                      Broadcast client or not."
        DEFVAL { disabled }
        ::= { ntpGrp 1 }

ntpBcastDelay OBJECT-TYPE
        SYNTAX        INTEGER (1..999999)
        MAX-ACCESS    read-write
        STATUS        current
        DESCRIPTION   "Estimated Round trip time (in micro seconds) for
                      NTP broadcasts. The range is from 1 to 999999."
        DEFVAL { 3000 }
        ::= { ntpGrp 2 }

ntpClient OBJECT-TYPE
        SYNTAX        INTEGER { enabled(1), disabled(2) }
        MAX-ACCESS    read-write
        STATUS        current
        DESCRIPTION   "Entry which tells if the device can act as a NTP
                      client (in a client-server configuration type)."
        DEFVAL { disabled }
        ::= { ntpGrp 3 }

ntpServerTable OBJECT-TYPE
        SYNTAX        SEQUENCE OF NtpServerEntry
        MAX-ACCESS    not-accessible
        STATUS        current
        DESCRIPTION   "A list of NTP Server entries. This table lists a
                      maximum of 10 Entries."
        ::= { ntpGrp 4 }

ntpServerEntry OBJECT-TYPE
        SYNTAX        NtpServerEntry
        MAX-ACCESS    not-accessible
        STATUS        current
        DESCRIPTION   "Entry containing NTP information for a particular
                      entry."
        INDEX         { ntpServerAddress }
        ::= { ntpServerTable 1 }

NtpServerEntry ::= SEQUENCE {
                ntpServerAddress
                            IpAddress,
                ntpServerType
                            INTEGER,
                ntpServerPublicKey
                            Unsigned32
        }

ntpServerAddress OBJECT-TYPE
        SYNTAX        IpAddress
        MAX-ACCESS    read-only
        STATUS        current
        DESCRIPTION   "Entry containing NTP Server's IP address."
        ::= { ntpServerEntry 1 }

ntpServerType OBJECT-TYPE
        SYNTAX        INTEGER{
                                valid(1),   -- add this entry
                                invalid(2)  -- remove this entry
                             }
        MAX-ACCESS    read-write
        STATUS        current
        DESCRIPTION   "To add or remove an entry to ntpServerTable.
                      Setting to 1 adds the entry and setting to 2
                      clears the entry."
        ::= { ntpServerEntry 2 }

ntpServerPublicKey OBJECT-TYPE
        SYNTAX        Unsigned32
        MAX-ACCESS    read-write
        STATUS        current
        DESCRIPTION   "The key to be used when communicating with this
                      server.
                      A key with a value of zero indicates an invalid
                      ntpServerPublicKey. When the authentication
                      feature is enabled the system will not sync with
                      this server when ntpAuthenticationPublicKey
                      doesn't match with NTP Packet's public key.
                        or
                      If the ntpAuthenticationTrustedMode is trusted but
                      encrypted message of ntpAuthenticationSecretKey
                      with NTP packet's data doesn't match with NTP
                      packet's crypto checksum in the message
                      authentication mode (MAC).
                        or
                      If the ntpAuthenticationTrustedMode is untrusted.

                      In client mode NMP will not send request NTP
                      Packet to the server when ntpServerPublicKey
                      doesn't match with any of the
                      ntpAuthenticationPublicKey in
                      ntpAuthenticationTable.
                        or
                      If the ntpAuthenticationTrustedMode is untrusted."
        ::= { ntpServerEntry 3 }

ntpSummertimeStatus OBJECT-TYPE
        SYNTAX        INTEGER { enabled(1),  disabled(2) }
        MAX-ACCESS    read-write
        STATUS        current
        DESCRIPTION   "Enabling or Disabling will set the clock ahead or
                      behind 1 hour respectively.(daylight savings time
                      in USA). This command gets active only in Summer
                      time."
        DEFVAL { disabled }
        ::= { ntpGrp 5 }

ntpSummerTimezoneName OBJECT-TYPE
        SYNTAX        DisplayString (SIZE (0..20))
        MAX-ACCESS    read-write
        STATUS        current
        DESCRIPTION   "Summertime time zone name for display purposes."
        ::= { ntpGrp 6 }

ntpTimezoneName OBJECT-TYPE
        SYNTAX        DisplayString (SIZE (0..20))
        MAX-ACCESS    read-write
        STATUS        current
        DESCRIPTION   "Time zone name for display purposes."
        ::= { ntpGrp 7 }

ntpTimezoneOffsetHour OBJECT-TYPE
        SYNTAX        INTEGER (-12..12)
        MAX-ACCESS    read-write
        STATUS        current
        DESCRIPTION   "Time offset (Hour) from Greenwich Mean Time."
        ::= { ntpGrp 8 }

ntpTimezoneOffsetMinute OBJECT-TYPE
        SYNTAX        INTEGER (0..59)
        MAX-ACCESS    read-write
        STATUS        current
        DESCRIPTION   "Time offset (Minutes) from Greenwich Mean Time."
        ::= { ntpGrp 9 }


ntpAuthenticationEnable OBJECT-TYPE
        SYNTAX        INTEGER { enabled(1),  disabled(2) }
        MAX-ACCESS    read-write
        STATUS        current
        DESCRIPTION   "Specifies if authentication feature is enabled or
                      disabled in the system."
        DEFVAL { disabled }
        ::= { ntpGrp 10 }

ntpAuthenticationTable OBJECT-TYPE
        SYNTAX        SEQUENCE OF NtpAuthenticationEntry
        MAX-ACCESS    not-accessible
        STATUS        current
        DESCRIPTION   "A list of NTP Authentication Key entries.
                      This table lists a maximum of 10 Entries"
::= { ntpGrp 11 }

ntpAuthenticationEntry OBJECT-TYPE
        SYNTAX        NtpAuthenticationEntry
        MAX-ACCESS    not-accessible
        STATUS        current
        DESCRIPTION   "An entry in the ntpAuthenticationTable,
                      containing values of an NTP authentication key
                      pair."

        INDEX         { ntpAuthenticationPublicKey }
        ::= { ntpAuthenticationTable 1 }

NtpAuthenticationEntry ::=
     SEQUENCE {
        ntpAuthenticationPublicKey
                Unsigned32,
        ntpAuthenticationSecretKey
                DisplayString,
        ntpAuthenticationTrustedMode
                INTEGER,
        ntpAuthenticationType
                INTEGER
    }

ntpAuthenticationPublicKey OBJECT-TYPE
        SYNTAX        Unsigned32
        MAX-ACCESS    read-only
        STATUS        current
        DESCRIPTION   "A unique value to identify the authentication
                      key. When the authentication feature is enabled
                      and the ntpAuthenticationPublicKey matches with
                      the NTP packet's public key then this entry is
                      used."
::= { ntpAuthenticationEntry 1}

ntpAuthenticationSecretKey OBJECT-TYPE
        SYNTAX        DisplayString (SIZE (1..32))
        MAX-ACCESS    read-write
        STATUS        current
        DESCRIPTION   "An arbitrary string known as the secret key used
                      for encrypting of the NTP packet. This key is
                      useful when the ntpAuthenticationTrustedMode is
                      set to trusted(1).
                      This key has to be specified when this
                      ntpAuthenticationEntry is created. When reading
                      this object, it will return empty string."
::= { ntpAuthenticationEntry 2}

ntpAuthenticationTrustedMode OBJECT-TYPE
        SYNTAX        INTEGER {
                              trusted(1),
                              untrusted(2)
                              }
        MAX-ACCESS    read-write
        STATUS        current
        DESCRIPTION   "A flag indicates whether the
                      ntpAuthenticationSecretKey is trusted or
                      untrusted. Setting a ntpAuthenticationSecretKey
                      to trusted(1) allows authentication on NTP
                      packets containing this key, and setting a
                      ntpAuthenticationSecretKey to untrusted(2) drops
                      all NTP packets containing this key."
::= { ntpAuthenticationEntry 3}

ntpAuthenticationType OBJECT-TYPE
        SYNTAX        INTEGER {
                               valid(1),        -- add this entry
                               invalid(2)       -- remove this entry
                              }
        MAX-ACCESS    read-write
        STATUS        current
        DESCRIPTION   "To add or remove an entry to
                      ntpAuthenticationTable. Setting to 1 adds the
                      entry and setting to 2 clears the entry."
::= { ntpAuthenticationEntry 4}



-- the TACACS (net.itransformers.topologyviewer.impl.Terminal Access Controller Access Control System) group

-- Implementation of the TACACS group is optional, but within the group
-- all the elements are current. If the TACACS+ feature is
-- implemented, the entire group should be implemented.

tacacsLoginAuthentication OBJECT-TYPE
        SYNTAX        INTEGER {
                                enabled(1),
                                disabled(2),
                                enabledForTelnetOnly(3),
                                enabledForConsoleOnly(4)
                              }
        MAX-ACCESS    read-write
        STATUS        deprecated
        DESCRIPTION   "Indicates whether the login authentication using
                      the TACACS+ feature is enabled or disabled for
                      console sessions and/or telnet sessions.

                      Setting this object to enabled(1), the login
                      authentication using the TACACS+ feature is
                      enabled for both telnet and console sessions.

                      Setting this object to disabled(2), the login
                      authentication using the TACACS+ feature is
                      disabled for both telnet and console sessions.

                      Setting this object to enabledForTelnetOnly(3),
                      the login authentication using the TACACS+
                      feature is enabled only for telnet sessions, but
                      disabled for console sessions.

                      Setting this object to enabledForConsoleOnly(4),
                      the login authentication using the TACACS+
                      feature is enabled only for console sessions,
                      but disabled for telnet sessions.

                      This object is deprecated and replaced by
                      cacPriorityTable in CISCO-AAA-CLIENT-MIB."
        DEFVAL { disabled }
        ::= { tacacsGrp 1 }

tacacsEnableAuthentication OBJECT-TYPE
        SYNTAX        INTEGER {
                                enabled(1),
                                disabled(2),
                                enabledForTelnetOnly(3),
                                enabledForConsoleOnly(4)
                              }
        MAX-ACCESS    read-write
        STATUS        deprecated
        DESCRIPTION   "Indicates whether the enable authentication using
                      the TACACS+ feature is enabled or disabled for
                      console sessions and/or telnet sessions based on
                      the value.

                      Setting this object to enabled(1), the enable
                      authentication using the TACACS+ feature is
                      enabled for both telnet and console sessions.

                      Setting this object to disabled(2), the enable
                      authentication using the TACACS+ feature is
                      disabled for both telnet and console sessions.

                      Setting this object to enabledForTelnetOnly(3),
                      the enable authentication using the TACACS+
                      feature is enabled only for telnet sessions, but
                      disabled for console sessions.

                      Setting this object to enabledForConsoleOnly(4),
                      the enable authentication using the TACACS+
                      feature is enabled only for console sessions,
                      but disabled for telnet sessions.

                      This object is deprecated and replaced by
                      cacPriorityTable in CISCO-AAA-CLIENT-MIB."
        DEFVAL { disabled }
        ::= { tacacsGrp 2 }

tacacsLocalLoginAuthentication OBJECT-TYPE
        SYNTAX        INTEGER {
                                enabled(1),
                                disabled(2),
                                enabledForTelnetOnly(3),
                                enabledForConsoleOnly(4)
                              }
        MAX-ACCESS    read-write
        STATUS        deprecated
        DESCRIPTION   "Indicates whether the login authentication using
                      local password is enabled or disabled for Console
                      session and/or Telnet session based on the value.

                      Setting this object to enabled(1),the login
                      authentication using local password is enabled for
                      both telnet and console sessions.

                      Setting this object to disabled(2), the login
                      authentication using local password is disabled
                      for both telnet and console sessions.

                      Setting this object to enabledForTelnetOnly(3),
                      the login authentication using local password is
                      enabled only for telnet sessions, but disabled for
                      console session.

                      Setting this object to enabledForConsoleOnly(4),
                      the login authentication using local password is
                      enabled only for console session, but disabled for
                      telnet sessions.

                      This object is deprecated and replaced by
                      cacPriorityTable in CISCO-AAA-CLIENT-MIB."
        DEFVAL { enabled }
        ::= { tacacsGrp 3 }

tacacsLocalEnableAuthentication OBJECT-TYPE
        SYNTAX        INTEGER {
                                enabled(1),
                                disabled(2),
                                enabledForTelnetOnly(3),
                                enabledForConsoleOnly(4)
                              }
        MAX-ACCESS    read-write
        STATUS        deprecated
        DESCRIPTION   "Indicates whether the enable authentication using
                      local password is enabled or disabled for Console
                      session and/or Telnet sessions.

                      Setting this object to enabled(1),the enable
                      authentication using local password is enabled for
                      both telnet and console sessions.

                      Setting this object to disabled(2), the enable
                      authentication using local password is disabled
                      for both telnet and console sessions.

                      Setting this object to enabledForTelnetOnly(3),
                      the enable authentication using local password is
                      enabled only for telnet sessions, but disabled for
                      console sessions.

                      Setting this object to enabledForConsoleOnly(4),
                      the enable authentication using local password is
                      enabled only for console sessions, but disabled
                      for telnet sessions.

                      This object is deprecated and replaced by
                      cacPriorityTable in CISCO-AAA-CLIENT-MIB."
         DEFVAL { enabled }
        ::= { tacacsGrp 4 }

tacacsNumLoginAttempts OBJECT-TYPE
        SYNTAX        INTEGER (1..10)
        MAX-ACCESS    read-write
        STATUS        deprecated
        DESCRIPTION   "The number of login attempts allowed.

                      This object is deprecated and replaced by
                      cacMaxLoginAttempt in CISCO-AAA-CLIENT-MIB."
        DEFVAL { 3 }
        ::= { tacacsGrp 5 }

tacacsDirectedRequest OBJECT-TYPE
        SYNTAX        INTEGER { enabled(1), disabled(2) }
        MAX-ACCESS    read-write
        STATUS        current
        DESCRIPTION   "Indicates whether the directed-request feature of
                      TACACS+ is enabled or disabled."
        DEFVAL { disabled }
        ::= { tacacsGrp 6 }

tacacsTimeout OBJECT-TYPE
        SYNTAX        INTEGER (1..255)
        MAX-ACCESS    read-write
        STATUS        deprecated
        DESCRIPTION   "The duration in seconds to wait for a response
                      from the TACACS+ server host.

                      This object is deprecated and replaced by
                      cacLockoutPeriodExt in CISCO-AAA-CLIENT-MIB."
        DEFVAL { 5 }
        ::= { tacacsGrp 7 }

tacacsAuthKey OBJECT-TYPE
        SYNTAX        DisplayString (SIZE(0..100))
        MAX-ACCESS    read-write
        STATUS        current
        DESCRIPTION   "The key used in encrypting the packets passed
                      between the TACACS+ server and the client. This
                      key must match the one configured on the server.

                      Note that this item is only accessible when using
                      the community string defined in sysCommunityRwa."
--      DEFVAL { NULL }
        ::= { tacacsGrp 8 }

tacacsServerTable OBJECT-TYPE
        SYNTAX        SEQUENCE OF TacacsServerEntry
        MAX-ACCESS    not-accessible
        STATUS        current
        DESCRIPTION   "This table lists a maximum of 3 TACACS+ servers."
        ::= { tacacsGrp 9 }

tacacsServerEntry OBJECT-TYPE
        SYNTAX        TacacsServerEntry
        MAX-ACCESS    not-accessible
        STATUS        current
        DESCRIPTION   "A TACACS+ server table entry."
        INDEX         { tacacsServerAddr }
        ::= { tacacsServerTable 1 }

TacacsServerEntry ::=
        SEQUENCE {
                tacacsServerAddr
                        IpAddress,
                tacacsServerType
                        INTEGER
        }

tacacsServerAddr OBJECT-TYPE
        SYNTAX        IpAddress
        MAX-ACCESS    read-only
        STATUS        current
        DESCRIPTION   "The IP address of a TACACS+ Server."
        ::= { tacacsServerEntry 1 }

tacacsServerType OBJECT-TYPE
        SYNTAX        INTEGER {
                                 invalid(1),   -- remove this entry
                                 primary(2),   -- the primary entry
                                 other(3)      -- a lower priority entry
                               }
        MAX-ACCESS    read-create
        STATUS        current
        DESCRIPTION   "To add a new entry to the tacacsServerTable, set
                      this object to primary(2) or other(3) for an IP
                      address which is not already in the table. The
                      primary entry will be used first, if it is
                      reachable. Otherwise, one of the other entries
                      will be used. Setting one entry to primary(2)
                      causes any previous primary entry to change to
                      other(3). To remove an entry from the table, set
                      this object to invalid(1)."
        ::= { tacacsServerEntry 2 }



-- the ip permit list group

-- Implementation of the ip permit list group is optional, but within
-- the group all the elements are current. If the ip permit list
-- feature is supported, the entire group should be implemented.

ipPermitEnable OBJECT-TYPE
        SYNTAX        INTEGER {
                                enabled(1),
                                disabled(2),
                                enabledForTelnetOnly(3),
                                enabledForSnmpOnly(4)
                              }
        MAX-ACCESS    read-write
        STATUS        deprecated
        DESCRIPTION   "This is deprecated and replaced by
                      ipPermitAccessTypeEnable.

                      Indicate whether the IP permit feature is enabled
                      or disabled for Telnet and/or SNMP.

                      Setting this object to enabled(1), the IP permit
                      feature is enabled for both telnet and SNMP.

                      Setting this object to disabled(2), the IP permit
                      feature is disabled for both telnet and SNMP.

                      Setting this object to enabledForTelnetOnly(3),
                      the IP permit feature is enabled for Telnet, but
                      disabled for the rest.

                      Setting this object to enabledForSnmpOnly(4), the
                      IP permit feature is enabled for SNMP, but
                      disabled for the rest."
        DEFVAL { disabled }
        ::= { ipPermitListGrp 1 }

-- the ip permit list table

ipPermitListTable OBJECT-TYPE
        SYNTAX        SEQUENCE OF IpPermitListEntry
        MAX-ACCESS    not-accessible
        STATUS        current
        DESCRIPTION   "This table lists a maximum of 100 IP Addresses
                      with net masks of IP permit hosts. If
                      ipPermitEnable is set to enabled(1), the system
                      will only accept inbound accesses which come from
                      the configured hosts with their permit access
                      types in this table."
        ::= { ipPermitListGrp 2 }

ipPermitListEntry OBJECT-TYPE
        SYNTAX        IpPermitListEntry
        MAX-ACCESS    not-accessible
        STATUS        current
        DESCRIPTION   "A IP permit list table entry."
        INDEX         { ipPermitAddress, ipPermitMask }
        ::= { ipPermitListTable 1 }

IpPermitListEntry ::=
        SEQUENCE {
                ipPermitAddress
                        IpAddress,
                ipPermitMask
                        IpAddress,
                ipPermitType
                        INTEGER,
                ipPermitAccessType
                        BITS,
                ipPermitTelnetConnectLimit
                        Unsigned32,
                ipPermitSshConnectLimit
                        Unsigned32
        }

ipPermitAddress OBJECT-TYPE
        SYNTAX        IpAddress
        MAX-ACCESS    read-only
        STATUS        current
        DESCRIPTION   "The IP address of a IP permit host."
        ::= { ipPermitListEntry 1 }


ipPermitMask OBJECT-TYPE
        SYNTAX        IpAddress
        MAX-ACCESS    read-only
        STATUS        current
        DESCRIPTION   "The IP net mask of a IP permit host."
        ::= { ipPermitListEntry 2 }

ipPermitType OBJECT-TYPE
        SYNTAX        INTEGER {
                              valid(1),  --add this entry
                              invalid(2) --remove this entry
                        }
        MAX-ACCESS    read-create
        STATUS        current
        DESCRIPTION   "Setting this object to invalid(2), removes the
                      corresponding entry from the ipPermitListTable. To
                      add a new entry into ipPermitListTable, set this
                      object to valid(1), for an IP address and IP net
                      mask which are not already in the table."
        ::= { ipPermitListEntry 3 }

ipPermitAccessType OBJECT-TYPE
        SYNTAX        BITS {
                                telnet(0),
                                snmp(1),
                                ssh(2),
                                http(3)
                      }
        MAX-ACCESS    read-create
        STATUS        current
        DESCRIPTION   "The IP access type of a IP permit host.
                      At least one access type has to be set."
        DEFVAL {{ telnet, snmp, ssh, http }}
        ::= { ipPermitListEntry 4 }

ipPermitTelnetConnectLimit OBJECT-TYPE
        SYNTAX          Unsigned32
        MAX-ACCESS      read-create
        STATUS          current
        DESCRIPTION     "Indicates the telnet connection limit that 
                        will be applied when accepting new telnet 
                        connections for a specific host. A value of 
                        zero means no limit will be applied for telnet 
                        connections.
 
       			Setting this object to a non-zero value will
		        turn on the 'telnet' bit in the corresponding 
		        ipPermitAccessType. Turnning off the 'telnet' 
		        bit in the corresponding ipPermitAccessType will
		        reset this ipPermitTelnetConnectLimit value to
		        zero."
        DEFVAL          { 0 }
    	::= { ipPermitListEntry 5 }
        
ipPermitSshConnectLimit OBJECT-TYPE
        SYNTAX          Unsigned32
        MAX-ACCESS      read-create
        STATUS          current
        DESCRIPTION     "Indicates the ssh connection limit that will 
       			be applied when accepting new ssh connections 
       			for a specific host. A value of zero means no 
       			limit will be applied for ssh connections.
 
       			Setting this object to a non-zero value will
		        turn on the 'ssh' bit in the corresponding 
		        ipPermitAccessType. Turnning off the 'ssh' bit 
		        in the corresponding ipPermitAccessType will
		        reset this ipPermitSshConnectLimit value to
		        zero."
        DEFVAL          { 0 }
    	::= { ipPermitListEntry 6 }

ipPermitDeniedListTable OBJECT-TYPE
        SYNTAX        SEQUENCE OF IpPermitDeniedListEntry
        MAX-ACCESS    not-accessible
        STATUS        current
        DESCRIPTION   "This table lists up to 10 the most recently
                      denied IP addresses with the access type."
        ::= { ipPermitListGrp 3 }

ipPermitDeniedListEntry OBJECT-TYPE
        SYNTAX        IpPermitDeniedListEntry
        MAX-ACCESS    not-accessible
        STATUS        current
        DESCRIPTION   "A IP permit denied list table entry."
        INDEX         {ipPermitDeniedAddress}
        ::= { ipPermitDeniedListTable 1}

IpPermitDeniedListEntry ::=
        SEQUENCE {
                ipPermitDeniedAddress
                        IpAddress,
                ipPermitDeniedAccess
                        INTEGER,
                ipPermitDeniedTime
                        TimeTicks
        }

ipPermitDeniedAddress OBJECT-TYPE
        SYNTAX        IpAddress
        MAX-ACCESS    read-only
        STATUS        current
        DESCRIPTION   "The IP address of a IP permit denied access."
        ::= { ipPermitDeniedListEntry 1 }

ipPermitDeniedAccess OBJECT-TYPE
        SYNTAX        INTEGER { telnet(1), snmp(2), ssh(3), http(4) }
        MAX-ACCESS    read-only
        STATUS        current
        DESCRIPTION   "The denied access type."
        ::= { ipPermitDeniedListEntry 2 }

ipPermitDeniedTime OBJECT-TYPE
        SYNTAX        TimeTicks
        MAX-ACCESS    read-only
        STATUS        current
        DESCRIPTION   "The time (in hundredths of a second) since the IP
                      permit denied access happens."
        ::= { ipPermitDeniedListEntry 3 }


ipPermitAccessTypeEnable OBJECT-TYPE
        SYNTAX        BITS {
                                telnet(0),
                                snmp(1),
                                ssh(2),
                                http(3)
                              }
        MAX-ACCESS    read-write
        STATUS        current
        DESCRIPTION   "This is to replace ipPermitEnable.
                      Indicates whether the IP permit feature is
                      enabled or disabled for Telnet, SNMP, ssh and
                      http. If a bit is set the coresponding feature is
                      enabled. If a bit is not set the coresponding
                      feature is disabled."
        DEFVAL { { } }
        ::= { ipPermitListGrp 4 }



-- the portChannel group

-- the port channel table

portChannelTable OBJECT-TYPE
        SYNTAX        SEQUENCE OF PortChannelEntry
        MAX-ACCESS    not-accessible
        STATUS        deprecated
        DESCRIPTION   "A list of port channel entries. The number of
                      entries is determined by the number of ports in
                      the system which support the Ethernet Channelling
                      feature.

                      This table is deprecated and replaced by
                      pagpEtherChannelTable in CISCO-PAGP-MIB and
                      dot3adAggTable in IEEE8023-LAG-MIB."
        ::= { portChannelGrp 1 }

portChannelEntry OBJECT-TYPE
        SYNTAX        PortChannelEntry
        MAX-ACCESS    not-accessible
        STATUS        deprecated
        DESCRIPTION   "Entry containing information for a particular
                      port on a module."
        INDEX         { portChannelModuleIndex, portChannelPortIndex }
        ::= { portChannelTable 1 }

PortChannelEntry ::=
        SEQUENCE {
                portChannelModuleIndex
                        INTEGER,
                portChannelPortIndex
                        INTEGER,
                portChannelPorts
                        OCTET STRING,
                portChannelAdminStatus
                        INTEGER,
                portChannelOperStatus
                        INTEGER,
                portChannelNeighbourDeviceId
                        OCTET STRING,
                portChannelNeighbourPortId
                        INTEGER,
                portChannelProtInPackets
                        Counter32,
                portChannelProtOutPackets
                        Counter32,
                portChannelIfIndex
                        INTEGER
        }

portChannelModuleIndex OBJECT-TYPE
        SYNTAX        INTEGER (1..16)
        MAX-ACCESS    read-only
        STATUS        deprecated
        DESCRIPTION   "An index value that uniquely identifies the
                      module where this port is located."
        ::= { portChannelEntry 1 }

portChannelPortIndex OBJECT-TYPE
        SYNTAX        INTEGER (1..255)
        MAX-ACCESS    read-only
        STATUS        deprecated
        DESCRIPTION   "An index value that uniquely identifies this port
                      within a module (see portIndex)."
        ::= { portChannelEntry 2 }

portChannelPorts OBJECT-TYPE
        SYNTAX        OCTET STRING (SIZE (0..8))
        MAX-ACCESS    read-write
        STATUS        deprecated
        DESCRIPTION   "The set of ports on a module channelling
                      together. Each Octet within the value of this
                      object specifies a set of eight ports, with the
                      first octet specifying ports 1 through 8, the
                      second octet specifying ports 9 through 16, etc.
                      Within each octet, the most significant bit
                      represents the lowest numbered port, and the
                      least significant bit rep resents the highest
                      numbered port. Thus, each port is represented by
                      a single bit within the value of this object. If
                      that bit has a value of `1' then that port is
                      included in the set of channel ports. The default
                      value of this object is a string which only has a
                      value of `1' on its own port."
        ::= { portChannelEntry 3 }

portChannelAdminStatus OBJECT-TYPE
        SYNTAX        INTEGER { on(1),
                                off(2),
                                desirable(3),
                                auto(4),
                                desirableSilent(5),
                                autoSilent(6) }

        MAX-ACCESS    read-write
        STATUS        deprecated
        DESCRIPTION   "Indicates the administrative status set on the
                      channel ports. If the status is set to on(1), the
                      channelling is enabled. If the status is set to
                      off(2), the channelling is disabled. If the status
                      is set to desirable(3), the port initiates a pagp
                      negotiation request to become a channel and will
                      become a channel if the far end agrees. If the
                      status is set to auto(4), the port does not
                      initiate a request to become a channel but will do
                      so if it receives a request to become a channel
                      from the far end. If the status is set to
                      desirableSilent(5), the port initiates a pagp
                      negotiation request to become a channel and will
                      become a channel if the far end agrees. If the
                      port doesn't receive any packets from far end,
                      then  after some timeout period the port forms a
                      channel by itself. If the status is set to
                      autoSilent(6), the port does not initiate a
                      request to become a channel, but will do so if it
                      receives a request to become a channel from the
                      far end. If the port doesn't receive any request,
                      then after some timeout period the port forms a
                      channel by itself."
        DEFVAL { auto }
        ::= { portChannelEntry 4 }

portChannelOperStatus OBJECT-TYPE
        SYNTAX        INTEGER { channelling(1), notChannelling(2) }
        MAX-ACCESS    read-only
        STATUS        deprecated
        DESCRIPTION   "Indicates whether the ports current channelling
                      operational status is channel or not."
        ::= { portChannelEntry 5 }

portChannelNeighbourDeviceId OBJECT-TYPE
        SYNTAX        OCTET STRING (SIZE (6))
        MAX-ACCESS    read-only
        STATUS        deprecated
        DESCRIPTION   "Indicates the neighbors device id."
        ::= { portChannelEntry 6 }

portChannelNeighbourPortId OBJECT-TYPE
        SYNTAX        INTEGER (1..2147483647)
        MAX-ACCESS    read-only
        STATUS        deprecated
        DESCRIPTION   "Indicates the neighbor ports' Id."
        ::= { portChannelEntry 7 }

portChannelProtInPackets OBJECT-TYPE
        SYNTAX        Counter32
        MAX-ACCESS    read-only
        STATUS        deprecated
        DESCRIPTION   "Indicates the number of protocol packets received
                      on the ports."
        ::= { portChannelEntry 8 }

portChannelProtOutPackets OBJECT-TYPE
        SYNTAX        Counter32
        MAX-ACCESS    read-only
        STATUS        deprecated
        DESCRIPTION   "Indicates the number of protocol packets
                      transmitted on the ports."
        ::= { portChannelEntry 9 }

portChannelIfIndex OBJECT-TYPE
        SYNTAX        INTEGER (1..2147483647)
        MAX-ACCESS    read-only
        STATUS        deprecated
        DESCRIPTION   "The value of the instance of the ifIndex object
                      defined in MIB-II, for the interface corresponding
                      to the channel which the port belongs to. This
                      object will have a non zero value if its
                      portChannelOperStatus is channelling and the link
                      of this port is up."
        ::= { portChannelEntry 10 }



-- the port capability
-- Implementation of the port capability group is optional, but within
-- the group all the elements are current.

portCpbTable OBJECT-TYPE
        SYNTAX        SEQUENCE OF PortCpbEntry
        MAX-ACCESS    not-accessible
        STATUS        current
        DESCRIPTION   "A list of port capability entries. The number of
                      entries is determined by the number of modules in
                      the chassis and the number of ports on each
                      module."
        ::= { portCpbGrp 1 }

portCpbEntry OBJECT-TYPE
        SYNTAX        PortCpbEntry
        MAX-ACCESS    not-accessible
        STATUS        current
        DESCRIPTION   "Entry containing port capability information for
                      a particular port on a module."
        INDEX         { portCpbModuleIndex, portCpbPortIndex }
        ::= { portCpbTable 1 }

PortCpbEntry ::=
        SEQUENCE {
                portCpbModuleIndex
                        INTEGER,
                portCpbPortIndex
                        INTEGER,
                portCpbSpeed
                        BITS,
                portCpbDuplex
                        BITS,
                portCpbTrunkEncapsulationType
                        BITS,
                portCpbTrunkMode
                        BITS,
                portCpbChannel
                        DisplayString,
                portCpbBroadcastSuppression
                        BITS,
                portCpbFlowControl
                        BITS,
                portCpbSecurity
                        INTEGER,
                portCpbVlanMembership
                        BITS,
                portCpbPortfast
                        INTEGER,
                portCpbUdld
                        INTEGER,
                portCpbInlinePower
                        BITS,
                portCpbAuxiliaryVlan
                        BITS,
                portCpbSpan
                        BITS,
                portCpbCosRewrite
                        INTEGER,
                portCpbTosRewrite
                        BITS,
                portCpbCopsGrouping
                        OCTET STRING,
                portCpbDot1x
                        INTEGER,
                portCpbIgmpFilter
                        INTEGER
        }

portCpbModuleIndex OBJECT-TYPE
        SYNTAX        INTEGER (1..16)
        MAX-ACCESS    read-only
        STATUS        current
        DESCRIPTION   "An index value that uniquely identifies the
                      module where this port is located (see
                      portModuleIndex)."
        ::= { portCpbEntry 1 }

portCpbPortIndex OBJECT-TYPE
        SYNTAX        INTEGER (1..255)
        MAX-ACCESS    read-only
        STATUS        current
        DESCRIPTION   "An index value that uniquely identifies this port
                      within a module (see portIndex)."
        ::= { portCpbEntry 2 }

portCpbSpeed OBJECT-TYPE
        SYNTAX        BITS { auto(0),
                             mbps4(1),
                             mbps10(2),
                             mbps16(3),
                             mbps45(4),
                             mbps100(5),
                             mbps155(6),
                             mbps400(7),
                             mbps622(8),
                             mbps1000(9),
                             mbps1dot544(10),  -- 1.544 mbps
                             mbps2(11),        -- 2 mbps
                             mbps2dot048(12),  -- 2.048 mbps
                             kps64(13),        -- 64 kps
                             mbps10000(14) }   -- 10 Gbps
        MAX-ACCESS    read-only
        STATUS        current
        DESCRIPTION   "Indicates the port speed capability of a port."
        ::= { portCpbEntry 3 }

portCpbDuplex OBJECT-TYPE
        SYNTAX        BITS { half(0),
                             full(1),
                             auto(2),
                             hdx(3),
                             fdx(4) }
        MAX-ACCESS    read-only
        STATUS        current
        DESCRIPTION   "Indicates the duplex capability of a port.
                      The fdx(4) is specially for tokenring full-duplex
                      and hdx(3) is specially for tokenring
                      half-duplex."
        ::= { portCpbEntry 4 }

portCpbTrunkEncapsulationType OBJECT-TYPE
        SYNTAX        BITS { lane(0),
                             dot10(1),
                             dot1Q(2),
                             isl(3),
                             negotiate(4) }
        MAX-ACCESS    read-only
        STATUS        current
        DESCRIPTION   "Indicates the VLAN encapsulation capability of a
                      port, The dot10(1) is for 801.10 and dot1q(2) is
                      for 801.1Q."
        ::= { portCpbEntry 5 }

portCpbTrunkMode OBJECT-TYPE
        SYNTAX        BITS { on(0),
                             off(1),
                             desirable(2),
                             auto(3),
                             onNoNegotiate(4) }
        MAX-ACCESS    read-only
        STATUS        current
        DESCRIPTION   "Indicates the trunk capability of a port."
        ::= { portCpbEntry 6 }

portCpbChannel OBJECT-TYPE
        SYNTAX        DisplayString (SIZE (0..128))
        MAX-ACCESS    read-only
        STATUS        current
        DESCRIPTION   "Indicates the channelling capability of a port."
        ::= { portCpbEntry 7 }

portCpbBroadcastSuppression OBJECT-TYPE
        SYNTAX        BITS { pps(0),
                             percentage(1) }
        MAX-ACCESS    read-only
        STATUS        current
        DESCRIPTION   "Indicates the broadcast suppression capability of
                      a port. The pps(0) is for ports capable of
                      specifying suppression in packets per second and
                      percentage(1) is for ports capable of specifying
                      suppression in terms of percentage of bandwidth."
        ::= { portCpbEntry 8 }

portCpbFlowControl OBJECT-TYPE
        SYNTAX        BITS { receiveOff(0),
                             receiveOn(1),
                             receiveDesired(2),
                             sendOff(3),
                             sendOn(4),
                             sendDesired(5) }
        MAX-ACCESS    read-only
        STATUS        current
        DESCRIPTION   "Indicates the flow control capability of a port."
        ::= { portCpbEntry 9 }

portCpbSecurity OBJECT-TYPE
        SYNTAX        INTEGER { yes(1), no(2) }
        MAX-ACCESS    read-only
        STATUS        current
        DESCRIPTION   "Indicates whether a port supports security."
        ::= { portCpbEntry 10 }

portCpbVlanMembership OBJECT-TYPE
        SYNTAX        BITS { static(0),
                             dynamic(1) }
        MAX-ACCESS    read-only
        STATUS        current
        DESCRIPTION   "Indicates the vlan membership capability of a
                      port."
        ::= { portCpbEntry 11 }

portCpbPortfast OBJECT-TYPE
        SYNTAX        INTEGER { yes(1), no(2) }
        MAX-ACCESS    read-only
        STATUS        current
        DESCRIPTION   "Indicates whether a port supports portfast."
        ::= { portCpbEntry 12 }

portCpbUdld OBJECT-TYPE
        SYNTAX        INTEGER {
                                yes(1),
                                no(2) }
        MAX-ACCESS    read-only
        STATUS        current
        DESCRIPTION   "Indicates whether the port is capable of UDLD
                      (UniDirectional Link Detection) or not."
        ::= { portCpbEntry 13 }

portCpbInlinePower OBJECT-TYPE
        SYNTAX        BITS {
                                auto(0),
                                on(1),
                                off(2),
                                static(3)
                              }
        MAX-ACCESS    read-only
        STATUS        current
        DESCRIPTION   "Indicate the inline power capability of a port.
                      'auto' denotes the ability that the switch
                      automatically determines whether or not power
                      should be provided. 'on' denotes the ability to
                      manually turn on inline power.
                      'off' denotes the ability to manually turn off
                      inline power. 'static' denotes the ability to
                      preallocate power for a port."
        ::= { portCpbEntry 14 }

portCpbAuxiliaryVlan OBJECT-TYPE
        SYNTAX  BITS {
                        vlanNo (0),
                        untagged (1),
                        dot1p (2),
                        none (3)
                     }
        MAX-ACCESS      read-only
        STATUS          current
        DESCRIPTION
            "Indicate the voice vlan capability of a port."
        ::= { portCpbEntry 15 }

portCpbSpan OBJECT-TYPE
        SYNTAX        BITS {
                                source(0),
                                destination(1),
                                reflector(2)
                           }
        MAX-ACCESS    read-only
        STATUS        current
        DESCRIPTION   "Indicates port span capabilities.
                      source(0) denotes the capability of being SPAN
                      source destination(1) denotes the capability of
                      being SPAN destination, reflector(2) denotes the
                      capability of being SPAN reflector."
        ::= { portCpbEntry 16 }

portCpbCosRewrite OBJECT-TYPE
        SYNTAX        INTEGER { yes(1), no(2) }
        MAX-ACCESS    read-only
        STATUS        current
        DESCRIPTION   "Indicates whether a port supports CoS rewrite."
        ::= { portCpbEntry 17 }

portCpbTosRewrite OBJECT-TYPE
        SYNTAX        BITS { dscp(0),
                             ipPrecedence(1) }
        MAX-ACCESS    read-only
        STATUS        current
        DESCRIPTION   "Indicates the ToS rewrite capability of a port.
                      dscp(0) denotes the port capability to classify
                      packets according to the DSCP.
                      ipPrecedence(1) denotes the port capability to
                      classify packets according to the IP Precedence."
        ::= { portCpbEntry 18 }

portCpbCopsGrouping OBJECT-TYPE
        SYNTAX        OCTET STRING (SIZE (0..8))
        MAX-ACCESS    read-only
        STATUS        current
        DESCRIPTION   "The set of ports on a module that are configured
                      together as far as the Differentiated Services
                      Cops feature is concerned. Each Octet within the
                      value of this object specifies a set of eight
                      ports, with the first octet specifying ports 1
                      through 8, the second octet specifying ports 9
                      through 16, etc. Within each octet, the most
                      significant bit represents the lowest numbered
                      port, and the least significant bit represents
                      the highest numbered port. Thus, each port is
                      represented by a single bit within the value of
                      this object. If that bit has a value of `1' then
                      that port is included in the set of Cops
                      grouping."
        ::= { portCpbEntry 19 }

portCpbDot1x OBJECT-TYPE
        SYNTAX        INTEGER { yes(1), no(2) }
        MAX-ACCESS    read-only
        STATUS        current
        DESCRIPTION   "Indicates whether a port supports 802.1x."
        ::= { portCpbEntry 20 }

portCpbIgmpFilter OBJECT-TYPE
        SYNTAX        INTEGER { yes(1), no(2) }
        MAX-ACCESS    read-only
        STATUS        current
        DESCRIPTION   "Indicates whether a port supports IGMP filter."
        ::= { portCpbEntry 21 }

-- The PORT Top "N" Group
--
-- The Port Top N group is used to prepare reports that
-- describe the ports that top a list ordered by one of
-- their statistics. Therefore, the sampling base is on
-- the ports in this monitored device system. The data
-- source is from all the ports in this monitored device
-- system so it is not necessary to specify the data
-- source in the control table.
-- The available statistics are samples of one of their
-- base statistics, over an interval specified by the
-- management station. Thus, these statistics are rate
-- based. The management station also selects how many such
-- ports are reported.
-- The portTopNControlTable is used to initiate the
-- generation of such a report. The management station
-- may select the parameters of such a report, such as
-- which statistic, how many ports, port types, and the start
-- and stop times of the sampling.

-- When the report is prepared, entries are created in the
-- portTopNTable associated with the relevant
-- portTopNControlEntry. These entries are static for
-- each report after it has been prepared.


portTopNControlTable OBJECT-TYPE
        SYNTAX        SEQUENCE OF PortTopNControlEntry
        MAX-ACCESS    not-accessible
        STATUS        current
        DESCRIPTION   "A list of top N port control entries."
        ::= { portTopNGrp 1 }

portTopNControlEntry OBJECT-TYPE
        SYNTAX        PortTopNControlEntry
        MAX-ACCESS    not-accessible
        STATUS        current
        DESCRIPTION   "A set of parameters that control the creation of
                      a report of the top N ports according to several
                      metrics.
                      For example, an instance of the portTopNDuration
                      object might be named portTopNDuration.3"
        INDEX         { portTopNControlIndex }
        ::= { portTopNControlTable 1 }

PortTopNControlEntry ::=
        SEQUENCE {
                portTopNControlIndex
                        INTEGER,
                portTopNRateBase
                        INTEGER,
                portTopNType
                        INTEGER,
                portTopNMode
                        INTEGER,
                portTopNReportStatus
                        INTEGER,
                portTopNDuration
                        INTEGER,
                portTopNTimeRemaining
                        INTEGER,
                portTopNStartTime
                        TimeTicks,
                portTopNRequestedSize
                        INTEGER,
                portTopNGrantedSize
                        INTEGER,
                portTopNOwner
                        OwnerString,
                portTopNStatus
                        RowStatus
        }

portTopNControlIndex OBJECT-TYPE
        SYNTAX        INTEGER (1..5)
        MAX-ACCESS    read-only
        STATUS        current
        DESCRIPTION   "An index that uniquely identifies an entry
                      in the portTopNControl table. Each such
                      entry defines one top N report."
        ::= { portTopNControlEntry 1 }

portTopNRateBase OBJECT-TYPE
        SYNTAX        INTEGER {
                                portTopNUtilization(1),
                                portTopNIOOctets(2),
                                portTopNIOPkts(3),
                                portTopNIOBroadcastPkts(4),
                                portTopNIOMulticastPkts(5),
                                portTopNInErrors(6),
                                portTopNBufferOverflow(7)
                      }
        MAX-ACCESS    read-create
        STATUS        current
        DESCRIPTION   "The variable for all ports in this system
                      based on which portTopNTable/report is ordered.

                      This object may not be modified if the associated
                      portTopNStatus object is equal to active(1)."
        DEFVAL { portTopNUtilization }
        ::= { portTopNControlEntry 2 }

portTopNType OBJECT-TYPE
        SYNTAX        INTEGER {
                                portTopNAllPorts(1),
                                portTopNEthernet(2),
                                portTopNFastEthernet(3),
                                portTopNGigaEthernet(4),
                                portTopNTokenRing(5),
                                portTopNFDDI(6),
                                portTopNAllEthernetPorts(7),
                                portTopN10GigaEthernet(8)
                      }
        MAX-ACCESS    read-create
        STATUS        current
        DESCRIPTION   "The sampling port type.

                      This object may not be modified if the associated
                      portTopNStatus object is equal to active(1)."
        DEFVAL { portTopNAllPorts }
        ::= { portTopNControlEntry 3 }

portTopNMode OBJECT-TYPE
        SYNTAX        INTEGER {
                                portTopNForeground(1),
                                portTopNBackground(2)
                      }
        MAX-ACCESS    read-create
        STATUS        current
        DESCRIPTION   "The running mode of this portTopN control entry.
                      portTopNForeground (1) means when
                      portTopNTimeRemaining reaches to 0, the report
                      will show on the CLI at once and it won't be kept
                      in the portTopNTable. portTopNBackground (2) means
                      the report will not show on the CLI it will be
                      kept in the portTopNTable.

                      This object may not be modified if the associated
                      portTopNStatus object is equal to active(1)."
        DEFVAL { portTopNBackground }
        ::= { portTopNControlEntry 4 }

portTopNReportStatus OBJECT-TYPE
        SYNTAX        INTEGER {
                                progressing(1),
                                ready(2)
                      }
        MAX-ACCESS    read-only
        STATUS        current
        DESCRIPTION   "The report status of this portTopN control entry.
                      Progressing (1) means that the report of this
                      portTopN control entry is still in progress. The
                      management station can poll this mib object to
                      check the report data is available or not.
                      Ready (2) means the report is available."
        ::= { portTopNControlEntry 5 }

portTopNDuration OBJECT-TYPE
        SYNTAX        INTEGER (0|10..999)
        MAX-ACCESS    read-create
        STATUS        current
        DESCRIPTION   "The sampling interval in seconds during which
                      statistics are collected for this report.

                      When this is set a value and the corresponding
                      portTopNControlEntry is valid, the
                      portTopNTimeRemaining object shall be set to the
                      same value.
                      portTopNTimeRemaining starts at the same value as
                      portTopNDuration and counts down as the collection
                      goes on.

                      If this object is set to be zero, it will do the
                      collection immediately. And the collecting report
                      value should be the absolute counter value."
        DEFVAL { 30 }
        ::= { portTopNControlEntry 6 }

portTopNTimeRemaining OBJECT-TYPE
        SYNTAX        INTEGER(1..65535)
        MAX-ACCESS    read-only
        STATUS        current
        DESCRIPTION   "The number of seconds left in the report
                      currently being collected. When portTopNDuration
                      object is modified by the management station, a
                      new collection is started, possibly aborting a
                      currently running report. The new value is used as
                      the requested duration of this report, which is
                      loaded from the associated portTopNDuration
                      object.

                      When this object is a non-zero value, any
                      associated portTopNEntries shall be made
                      inaccessible by the monitor.

                      While the value of this object is non-zero and the
                      corresponding portTopNControlENtry is valid, it
                      decrements by one per second until it reaches
                      zero. During this time, all associated
                      portTopNEntries shall remain inaccessible. At
                      the time that this object decrements to zero, the
                      report is made accessible in the portTopNTable.
                      Thus, the portTopN table is to be created only at
                      the end of the collection interval."
        ::= { portTopNControlEntry 7 }

portTopNStartTime OBJECT-TYPE
        SYNTAX        TimeTicks
        MAX-ACCESS    read-only
        STATUS        current
        DESCRIPTION   "The value of sysUpTime when this top N report was
                      last started. In other words, this is the time
                      that the associated portTopNTimeRemaining object
                      was modified to start the requested report."
        ::= { portTopNControlEntry 8 }

portTopNRequestedSize OBJECT-TYPE
        SYNTAX        INTEGER(1..65535)
        MAX-ACCESS    read-create
        STATUS        current
        DESCRIPTION   "The maximum number of ports requested for the top
                      N entry.

                      When this object is created or modified, the value
                      of portTopNGrantedSize is set as closely to this
                      object as is possible for the particular
                      implementation and available resources.
                      Valid value for this object is 1 to maximum number
                      of physical ports. The default value is 20 ports."
        DEFVAL { 20 }
        ::= { portTopNControlEntry 9 }

portTopNGrantedSize OBJECT-TYPE
        SYNTAX        INTEGER(1..65535)
        MAX-ACCESS    read-only
        STATUS        current
        DESCRIPTION   "The maximum number of ports in the top N table.
                      When the associated portTopNRequestedSize object
                      is created or modified, the value of this object
                      should be set as closely to the requested value as
                      is possible for the particular implementation and
                      available resources. The value must not be lowered
                      except as a result of a set to the associated
                      portTopNRequestedSize object.
                      Ports with the highest value of portTopNRateBase
                      shall be placed in this table in decreasing order
                      of this rate until there is no more room or until
                      there are no more ports."
        ::= { portTopNControlEntry 10 }

portTopNOwner OBJECT-TYPE
        SYNTAX        OwnerString
        MAX-ACCESS    read-create
        STATUS        current
        DESCRIPTION   "The entity that configured this entry and is
                      therefore using the resources assigned to it."
        ::= { portTopNControlEntry 11 }

portTopNStatus OBJECT-TYPE
        SYNTAX        RowStatus
        MAX-ACCESS    read-create
        STATUS        current
        DESCRIPTION   "The status of this portTopNControl entry.
                      The Management station sends the user set values
                      with a portTopNStatus value of createAndGo(4).
                      When the agent receives it the collection of the
                      report starts.
                      When the portTopNReportStatus is ready(2) the user
                      can get the reports (portTopNTable).
                      For the current implementation createAndWait(5)
                      will not be supported.
                      There can be only 5 rows in the control table."
        ::= { portTopNControlEntry 12 }

portTopNTable OBJECT-TYPE
        SYNTAX        SEQUENCE OF PortTopNEntry
        MAX-ACCESS    not-accessible
        STATUS        current
        DESCRIPTION   "A list of top N port entries."
        ::= { portTopNGrp 2 }

portTopNEntry OBJECT-TYPE
        SYNTAX        PortTopNEntry
        MAX-ACCESS    not-accessible
        STATUS        current
        DESCRIPTION   "A set of statistics for a port that is part of a
                      top N report. For example, an instance of the
                      portTopNRateBase object might be named
                      portTopNUtilization.3.10"
        INDEX         { portTopNControlIndex, portTopNIndex }
        ::= { portTopNTable 1 }

PortTopNEntry ::=
        SEQUENCE {
                portTopNIndex
                        INTEGER,
                portTopNModuleNumber
                        INTEGER,
                portTopNPortNumber
                        INTEGER,
                portTopNUtilization
                        INTEGER,
                portTopNIOOctets
                        Counter64,
                portTopNIOPkts
                        Counter64,
                portTopNIOBroadcast
                        Counter64,
                portTopNIOMulticast
                        Counter64,
                portTopNInErrors
                        Counter32,
                portTopNBufferOverFlow
                        Counter32
        }

portTopNIndex OBJECT-TYPE
        SYNTAX        INTEGER (1..65535)
        MAX-ACCESS    read-only
        STATUS        current
        DESCRIPTION   "An index that uniquely identifies an entry in
                      the portTopN table among those in the same report.
                      This index is between 1 and N, where N is the
                      portTopNGrantedSize of ports with the highest
                      portTopNRateBase. Increasing values of
                      portTopNIndex shall be assigned to entries with
                      decreasing values of portTopNRateBase until index
                      N is assigned to the entry with the lowest value
                      of portTopNRateBase or there are no more
                      portTopNEntries."
        ::= { portTopNEntry 1 }

portTopNModuleNumber OBJECT-TYPE
        SYNTAX        INTEGER (1..20)
        MAX-ACCESS    read-only
        STATUS        current
        DESCRIPTION   "The module number of the port counter data
                      entry."
        ::= { portTopNEntry 2 }

portTopNPortNumber OBJECT-TYPE
        SYNTAX        INTEGER (1..255)
        MAX-ACCESS    read-only
        STATUS        current
        DESCRIPTION   "The port number of the port counter data entry."
        ::= { portTopNEntry 3 }

portTopNUtilization OBJECT-TYPE
        SYNTAX        INTEGER(1..65535)
        MAX-ACCESS    read-only
        STATUS        current
        DESCRIPTION   "The utilization of the port in the system.
                      The utilization is computed in the following
                      methods:

              Ethernet Utilization: (If Full Duplex, multiply by 2)

              10 Mbps         I/O-pkts * (9.6 + 6.4) + (0.8 * I/O-Bytes)
              Ethernet Util = -----------------------------------------
                              Interval * 10,000

                              where 9.6 is interframe gap of Ethernet
                              6.4 is preamble of Ethernet
                              10,000 is 10Mbps

              100 Mbps        I/O-pkts * (96 + 64) + (8 * I/O-Bytes)
              Ethernet Util = --------------------------------------
                              Interval * 1,000,000

              1000 Mbps       I/O-pkts * (96 + 64) + (8 * I/O-Bytes)
              Ethernet Util = --------------------------------------
                              Interval * 10,000,000

              All other       I/O-pkts * (9.6 + 6.4) + (0.8 * I/O-Bytes)
              Ethernet Util = ------------------------------------------
                              Interval * N * 1,000
                              (where N is N Mbps)

              Token Ring Utilization:
                (Assuming that Octets is from AC byte through FCS)


              4 Mbps                  Pkts * 32 + (8 * Octets)
              Token Ring Util = 100 * ------------------------
                                      Interval * 4,000,000
                                 where 32 is bits in SD, ED, FS and IFG

              16 Mbps                 Pkts * 64 + (8 * Octets)
              Token Ring Util = 100 * ------------------------
                                      Interval * 16,000,000
                                where 64 is bits in SD, ED, FS and IFG

              FDDI Utilization:

                         I/O-Pkts * (64 + 8 + 32 + 16) + (8 * I/O-Bytes)
             FDDI Util = ----------------------------------------------
                         Interval * 100,000,000

                         where 64 is Preamble of FDDI,
                         8 is the Start Delimiter (SD) of FDDI,
                         32 is the CRC, and
                         16 is the End of Frame Sequence (EFS) of FDDI."

        ::= { portTopNEntry 4 }

portTopNIOOctets OBJECT-TYPE
        SYNTAX        Counter64
        MAX-ACCESS    read-only
        STATUS        current
        DESCRIPTION   "The Input and Output octets of the port in the
                      system."
        ::= { portTopNEntry 5 }

portTopNIOPkts OBJECT-TYPE
        SYNTAX        Counter64
        MAX-ACCESS    read-only
        STATUS        current
        DESCRIPTION   "The Input and Output packets of the port in the
                      system."
        ::= { portTopNEntry 6 }

portTopNIOBroadcast OBJECT-TYPE
        SYNTAX        Counter64
        MAX-ACCESS    read-only
        STATUS        current
        DESCRIPTION   "The Input and Output broadcast packets of the
                      port in the system."
        ::= { portTopNEntry 7 }

portTopNIOMulticast OBJECT-TYPE
        SYNTAX        Counter64
        MAX-ACCESS    read-only
        STATUS        current
        DESCRIPTION   "The Input and Output multicast packets of the
                       port in the system."
        ::= { portTopNEntry 8 }

portTopNInErrors OBJECT-TYPE
        SYNTAX        Counter32
        MAX-ACCESS    read-only
        STATUS        current
        DESCRIPTION   "The Input error packets of the port in the
                      system."
        ::= { portTopNEntry 9 }

portTopNBufferOverFlow OBJECT-TYPE
        SYNTAX        Counter32
        MAX-ACCESS    read-only
        STATUS        current
        DESCRIPTION   "The number of buffer overflow of the port in
                      the system."
        ::= { portTopNEntry 10 }



-- the multiple default gateway group

-- Implementation of the multiple default gateway group is optional,
-- but within the group all the elements are current. If the multiple
-- default gateway feature is supported, the entire group should be
-- implemented.

mdgGatewayTable OBJECT-TYPE
        SYNTAX        SEQUENCE OF MdgGatewayEntry
        MAX-ACCESS    not-accessible
        STATUS        current
        DESCRIPTION   "This table lists a maximum of 3 MDG gateways."
        ::= { mdgGrp 1 }

mdgGatewayEntry OBJECT-TYPE
        SYNTAX        MdgGatewayEntry
        MAX-ACCESS    not-accessible
        STATUS        current
        DESCRIPTION   "A MDG gateway table entry."
        INDEX         { mdgGatewayAddr }
        ::= { mdgGatewayTable 1 }

MdgGatewayEntry ::=
        SEQUENCE {
                mdgGatewayAddr
                        IpAddress,
                mdgGatewayType
                        INTEGER
        }

mdgGatewayAddr OBJECT-TYPE
        SYNTAX        IpAddress
        MAX-ACCESS    read-only
        STATUS        current
        DESCRIPTION   "The IP address of a default gateway."
        ::= { mdgGatewayEntry 1 }

mdgGatewayType OBJECT-TYPE
        SYNTAX        INTEGER {
                                 invalid(1),   -- remove this entry
                                 primary(2),   -- the primary entry
                                 other(3)      -- a lower priority entry
                               }
        MAX-ACCESS    read-create
        STATUS        current
        DESCRIPTION   "To add a new entry to the mdgGatewayTable, set
                      this object to primary(2) or other(3) for an IP
                      address which is not already in the table. The
                      primary entry will be used first, if it is
                      reachable. Otherwise, one of the other entries
                      will be used. Setting one entry to primary(2)
                      causes any previous primary entry to change to
                      other(3). To remove an entry from the table, set
                      this object to invalid(1). Changing an existing
                      entry from primary(2) to other(3) is not allowed.
                      If the value of this object is updated, the
                      corresponding entry of the ipRouteTable (mibII)
                      will be updated and vice versa."
        ::= { mdgGatewayEntry 2 }



-- the RADIUS group

-- Implementation of the RADIUS group is optional, but within the group
-- all the elements are current. If the RADIUS feature is implemented,
-- the entire group should be implemented.

radiusLoginAuthentication OBJECT-TYPE
        SYNTAX        INTEGER {
                                enabled(1),
                                disabled(2),
                                enabledForTelnetOnly(3),
                                enabledForConsoleOnly(4)
                              }
        MAX-ACCESS    read-write
        STATUS        deprecated
        DESCRIPTION   "Indicates whether the login authentication using
                      RADIUS feature is enabled or disabled for console
                      and/or telnet sessions.

                      Setting this object to enabled(1), the login
                      authentication using RADIUS feature is enabled for
                      both console and telnet sessions.

                      Setting this object to disabled(2), the login
                      authentication using RADIUS feature is disabled
                      for both console and telnet sessions.

                      Setting this object to enabledForTelnetOnly(3),the
                      login authentication using RADIUS feature is
                      enabled only for telnet sessions, but disabled
                      for console session.

                      Setting this object to enabledForConsoleOnly(4),
                      the login authentication using RADIUS feature is
                      enabled only for console sessions, but disabled
                      for telnet sessions.

                      This object is deprecated and replaced by
                      cacPriorityTable in CISCO-AAA-CLIENT-MIB."
        DEFVAL { disabled }
        ::= { radiusGrp 1 }

radiusEnableAuthentication OBJECT-TYPE
        SYNTAX        INTEGER {
                                enabled(1),
                                disabled(2),
                                enabledForTelnetOnly(3),
                                enabledForConsoleOnly(4)
                              }
        MAX-ACCESS    read-write
        STATUS        deprecated
        DESCRIPTION   "Indicates whether the enable authentication using
                      the RADIUS feature is enabled or disabled for
                      Console and telnet sessions.

                      Setting this object to enabled(1), the enable
                      authentication using RADIUS feature is enabled for
                      both console and telnet sessions.

                      Setting this object to disabled(2), the enable
                      authentication using RADIUS feature is disabled
                      for both console and telnet sessions.

                      Setting this object to enabledForTelnetOnly(3),
                      the enable authentication using RADIUS feature is
                      enabled only for telnet sessions, but disabled for
                      console sessions.

                      Setting this object to enabledForConsoleOnly(4),
                      the enable authentication using RADIUS feature is
                      enabled only for console sessions, but disabled
                      for telnet sessions.

                      This object is deprecated and replaced by
                      cacPriorityTable in CISCO-AAA-CLIENT-MIB."
        DEFVAL { disabled }
        ::= { radiusGrp 2 }

radiusDeadtime OBJECT-TYPE
        SYNTAX        INTEGER (0..1440)
        MAX-ACCESS    read-write
        STATUS        current
        DESCRIPTION   "Indicates the length of time in minutes that
                      the system will mark the server dead when a RADIUS
                      server does not respond to an authentication
                      request. During the interval of the dead time, any
                      authentication request that comes up would not be
                      sent to that RADIUS server that was marked as
                      dead. The default value of 0 means that the
                      RADIUS servers will not be marked dead if they
                      do not respond."
        DEFVAL { 0 }
        ::= { radiusGrp 3 }

radiusAuthKey OBJECT-TYPE
        SYNTAX        DisplayString (SIZE(0..64))
        MAX-ACCESS    read-write
        STATUS        current
        DESCRIPTION   "The key used in encrypting the packets passed
                      between the RADIUS server and the client. This key
                      must match the one configured on the server.

                      Note that this item is only accessible when using
                      the community string defined in sysCommunityRwa."
--      DEFVAL { NULL }
        ::= { radiusGrp 4 }

radiusTimeout OBJECT-TYPE
        SYNTAX        INTEGER (1..1000)
        MAX-ACCESS    read-write
        STATUS        current
        DESCRIPTION   "This is the time in seconds between
                      retransmissions to the RADIUS server."
        DEFVAL { 5 }
        ::= { radiusGrp 5 }


radiusRetransmits OBJECT-TYPE
        SYNTAX        INTEGER (1..100)
        MAX-ACCESS    read-write
        STATUS        current
        DESCRIPTION   "Indicates number of times the RADIUS server
                      should be tried before giving up on the server."
        DEFVAL { 2 }
        ::= { radiusGrp 6 }


radiusServerTable OBJECT-TYPE
        SYNTAX        SEQUENCE OF RadiusServerEntry
        MAX-ACCESS    not-accessible
        STATUS        deprecated
        DESCRIPTION   "This table lists a maximum of 3 RADIUS servers.

                      This object is deprecated and replaced by
                      crRadiusServerTable in CISCO-RADIUS-MIB."
        ::= { radiusGrp 7 }

radiusServerEntry OBJECT-TYPE
        SYNTAX        RadiusServerEntry
        MAX-ACCESS    not-accessible
        STATUS        deprecated
        DESCRIPTION   "A RADIUS server table entry."
        INDEX         { radiusServerAddr }
        ::= { radiusServerTable 1 }

RadiusServerEntry ::=
        SEQUENCE {
                radiusServerAddr
                        IpAddress,
                radiusServerAuthPort
                        INTEGER,
                radiusServerType
                        INTEGER
        }

radiusServerAddr OBJECT-TYPE
        SYNTAX        IpAddress
        MAX-ACCESS    read-only
        STATUS        deprecated
        DESCRIPTION   "The IP address of a RADIUS Server."
        ::= { radiusServerEntry 1 }

radiusServerAuthPort OBJECT-TYPE
        SYNTAX        INTEGER (0..65535)
        MAX-ACCESS    read-create
        STATUS        deprecated
        DESCRIPTION   "This is the destination UDP port number to which
                      RADIUS messages should be sent. The RADIUS server
                      will not be used for authentication if this port
                      number is 0."
        REFERENCE     "RFC2138, Implementation Note."
        DEFVAL { 1812 }
        ::= { radiusServerEntry 2 }

radiusServerType OBJECT-TYPE
        SYNTAX        INTEGER {
                                 invalid(1),   -- remove this entry
                                 primary(2),   -- the primary entry
                                 other(3)      -- a lower priority entry
                               }
        MAX-ACCESS    read-create
        STATUS        deprecated
        DESCRIPTION   "To add a new entry to the radiusServerTable, set
                      this object to primary(2) or other(3) for an IP
                      address which is not already in the table. The
                      primary entry will be used first, if it is
                      reachable. Otherwise, one of the other entries
                      will be used. Setting one entry to primary(2)
                      causes any previous primary entry to change to
                      other(3). To remove an entry from the table,
                      set this object to invalid(1)."
        ::= { radiusServerEntry 3 }

-- the traceRoute group

-- Implementation of the traceRoute group is optional, but within the
-- group all the elements are current. If the trace route feature is
-- supported, the entire group should be implemented.

traceRouteMaxQueries OBJECT-TYPE
        SYNTAX        INTEGER (1..20)
        MAX-ACCESS    read-only
        STATUS        current
        DESCRIPTION   "Maximum number of query entries allowed to be
                      outstanding at any time, in the
                      traceRouteQueryTable.
                      The typical value for this object is 5."
        ::= { traceRouteGrp 1}

traceRouteQueryTable OBJECT-TYPE
        SYNTAX        SEQUENCE OF TraceRouteQueryEntry
        MAX-ACCESS    not-accessible
        STATUS        current
        DESCRIPTION   "A control table used to query the information
                      about each gateway along the path to a host by
                      specifying retrieval criteria for the host. The
                      resulting data for each instance of a query in
                      this table is returned in the traceRouteDataTable.
                      The maximum number of entries (rows) in this table
                      cannot exceed the value returned by
                      traceRouteMaxQueries."
        ::= { traceRouteGrp 2         }

traceRouteQueryEntry OBJECT-TYPE
        SYNTAX        TraceRouteQueryEntry
        MAX-ACCESS    not-accessible
        STATUS        current
        DESCRIPTION   "A conceptual row of the traceRouteQueryTable used
                      to setup retrieval criteria to search for gateways
                      belongs to the path to a particular host
                      identified by its IP address. The actual search
                      is started by setting the value of
                      traceRouteQueryStatus to valid(1)."
        INDEX         { traceRouteQueryIndex }
        ::= { traceRouteQueryTable 1 }

TraceRouteQueryEntry  ::=
        SEQUENCE {
                traceRouteQueryIndex
                        INTEGER,
                traceRouteHost
                        DisplayString,
                traceRouteQueryDNSEnable
                        INTEGER,
                traceRouteQueryWaitingTime
                        INTEGER,
                traceRouteQueryInitTTL
                        INTEGER,
                traceRouteQueryMaxTTL
                        INTEGER,
                traceRouteQueryUDPPort
                        INTEGER,
                traceRouteQueryPacketCount
                        INTEGER,
                traceRouteQueryPacketSize
                        INTEGER,
                traceRouteQueryTOS
                        INTEGER,
                traceRouteQueryResult
                        INTEGER,
                traceRouteQueryTime
                        TimeTicks,
                traceRouteQueryOwner
                        DisplayString,
                traceRouteQueryStatus
                        INTEGER
        }


traceRouteQueryIndex OBJECT-TYPE
        SYNTAX        INTEGER (1..65535)
        MAX-ACCESS    read-only
        STATUS        current
        DESCRIPTION   "Object which specifies an unique entry in the
                      traceRouteQueryTable."
        ::= { traceRouteQueryEntry 1 }

traceRouteHost OBJECT-TYPE
        SYNTAX        DisplayString(SIZE(0..255))
        MAX-ACCESS    read-create
        STATUS        current
        DESCRIPTION   "Network(IP) address in dotted decimal format or
                     the DNS hostname of the host which is tracerouted."
        ::= { traceRouteQueryEntry 2 }

traceRouteQueryDNSEnable OBJECT-TYPE
        SYNTAX        INTEGER{ enabled(1),
                         disabled(2) }
        MAX-ACCESS    read-create
        STATUS        current
        DESCRIPTION   "If this value of this object is true, the
                      traceroute operation will do a DNS lookup for each
                      hop on the path, so the corresponding instance of
                      the traceRouteDataTable will contain the host name
                      and the ip address; otherwise, that instance only
                      contains the ip address."
        DEFVAL { enabled }
        ::= { traceRouteQueryEntry 3 }

traceRouteQueryWaitingTime OBJECT-TYPE
        SYNTAX        INTEGER (1..300)
        UNITS         "seconds"
        MAX-ACCESS    read-create
        STATUS        current
        DESCRIPTION   "The trace route waiting time in seconds for an
                      ICMP response message."
        DEFVAL { 5 }
        ::= { traceRouteQueryEntry 4 }

traceRouteQueryInitTTL OBJECT-TYPE
        SYNTAX        INTEGER(1..255)
        MAX-ACCESS    read-create
        STATUS        current
        DESCRIPTION   "If this value of this object is set, it allows
                      users skip processing for gateways that are less
                      than traceRouteQueryInitTTL away by sending
                      datagram with the value of this object instead of
                      the default value of one."
        DEFVAL { 1 }
        ::= { traceRouteQueryEntry 5 }

traceRouteQueryMaxTTL OBJECT-TYPE
        SYNTAX        INTEGER (1..255)
        MAX-ACCESS    read-create
        STATUS        current
        DESCRIPTION   "The maximum TTL value used in outgoing packets."
        DEFVAL { 30 }
        ::= { traceRouteQueryEntry 6}

traceRouteQueryUDPPort OBJECT-TYPE
        SYNTAX        INTEGER(1..65535)
        MAX-ACCESS    read-create
        STATUS        current
        DESCRIPTION   "The base UDP destination port is used in the
                      traceroute datagrams. This value of this object is
                      often larger than 30,000 to make it improbable
                      that this port is used (this causes the
                      destination host's UDP module to generate an ICMP
                      port unreachable so the traceroute operation
                      knows when the operation is accomplished).
                      The traceroute operation will increment this value
                      of this object each time it sends a datagram. This
                      object should be used in the unlikely event that
                      the destination port is listening to a port in the
                      default traceroute port range."
        DEFVAL { 33434 }
        ::= { traceRouteQueryEntry 7 }

traceRouteQueryPacketCount OBJECT-TYPE
        SYNTAX        INTEGER(1..1000)
        MAX-ACCESS    read-create
        STATUS        current
        DESCRIPTION   "Specifies the number of traceroute packets to
                      send to the target host in this sequence."
        DEFVAL { 3 }
        ::= { traceRouteQueryEntry 8 }

traceRouteQueryPacketSize OBJECT-TYPE
        SYNTAX        INTEGER(0..1420)
        MAX-ACCESS    read-create
        STATUS        current
        DESCRIPTION   "Specifies the size of traceroute packets to send
                      to the target host in this sequence. "
        DEFVAL { 0 }
        ::= { traceRouteQueryEntry 9 }

traceRouteQueryTOS OBJECT-TYPE
        SYNTAX        INTEGER(0..255)
        MAX-ACCESS    read-create
        STATUS        current
        DESCRIPTION   "The type of service to be set in the IP header of
                      the outgoing packets.This value can set to see if
                      different types-of-service result in different
                      paths. Not all values of TOS are legal or
                      meaningful (see the IP spec for definitions.
                      Useful values are probably 16 (low delay) and 8
                      (high throughput)."
        DEFVAL { 0 }
        ::= { traceRouteQueryEntry 10 }

traceRouteQueryResult OBJECT-TYPE
        SYNTAX        INTEGER(-1..2147483647)
        MAX-ACCESS    read-only
        STATUS        current
        DESCRIPTION   "The result status of the query. Possible values
                      are:

                      -1 -Either the query has not been initiated or the
                      agent is busy processing this query instance. Time
                      to completion of the query processing depends on
                      the complexity of the query and the number of
                      matches that satisfy this query.

                      0..2147483647 - The search has ended and this is
                      the number of rows in the traceRouteDataTable,
                      resulting from this query."
        ::= { traceRouteQueryEntry 21}

traceRouteQueryTime OBJECT-TYPE
        SYNTAX        TimeTicks
        MAX-ACCESS    read-only
        STATUS        current
        DESCRIPTION   "The value of sysUpTime at the time when the query
                      is configured."
        ::= { traceRouteQueryEntry 22 }

traceRouteQueryOwner OBJECT-TYPE
        SYNTAX        DisplayString (SIZE (0..50))
        MAX-ACCESS    read-create
        STATUS        current
        DESCRIPTION   "The manager entity that configured this entry and
                      is therefore using the resources assigned to it."
        ::= { traceRouteQueryEntry 23 }

traceRouteQueryStatus OBJECT-TYPE
        SYNTAX        INTEGER {valid(1), invalid(2) }
        MAX-ACCESS    read-create
        STATUS        current
        DESCRIPTION   "The status object used to manage rows in this
                      table.
                      When set this object to valid(1), the query is
                      initiated. Once initiated, all the read-write
                      objects of this table can't be modified. To remove
                      an entry from the  table, set this object to
                      invalid(2)."
        ::= { traceRouteQueryEntry 24 }

-- The Trace Route result table.

traceRouteDataTable OBJECT-TYPE
        SYNTAX        SEQUENCE OF TraceRouteDataEntry
        MAX-ACCESS    not-accessible
        STATUS        current
        DESCRIPTION   "A table containing information about the gateway
                      belongs to the path to the host corresponding to
                      all the completed queries setup in the
                      traceRouteQueryTable."
        ::= { traceRouteGrp 3 }

traceRouteDataEntry OBJECT-TYPE
        SYNTAX        TraceRouteDataEntry
        MAX-ACCESS    not-accessible
        STATUS        current
        DESCRIPTION   "A conceptual row of the traceRouteDataTable used
                      to return information about all the gateway
                      belongs to the host of which search criteria is
                      corresponding instance of the
                      traceRouteQueryTable."
        INDEX         { traceRouteQueryIndex, traceRouteDataIndex }
        ::= { traceRouteDataTable 1 }

TraceRouteDataEntry ::=
        SEQUENCE {
                traceRouteDataIndex
                        INTEGER,
                traceRouteDataGatewayName
                        DisplayString,
                traceRouteDataGatewayIp
                        IpAddress,
                traceRouteDataRtt
                        INTEGER,
                traceRouteDataHopCount
                        INTEGER,
                traceRouteDataErrors
                        INTEGER
        }

traceRouteDataIndex OBJECT-TYPE
        SYNTAX        INTEGER(1..65535)
        MAX-ACCESS    read-only
        STATUS        current
        DESCRIPTION   "Object which specifies an unique entry in the
                      traceRouteDataTable."
        ::= { traceRouteDataEntry 1 }

traceRouteDataGatewayName OBJECT-TYPE
        SYNTAX        DisplayString(SIZE(0..255))
        MAX-ACCESS    read-only
        STATUS        current
        DESCRIPTION   "The DNS name of the gateway if available."
        ::= { traceRouteDataEntry 2 }

traceRouteDataGatewayIp OBJECT-TYPE
        SYNTAX        IpAddress
        MAX-ACCESS    read-only
        STATUS        current
        DESCRIPTION   "The ip address of the gateway. If the traceroute
                      packet was sent and timed-out, the ip address is
                      set to 0.0.0.0."
        ::= { traceRouteDataEntry 3 }

traceRouteDataRtt OBJECT-TYPE
        SYNTAX        INTEGER(1..65535)
        UNITS         "milliseconds"
        MAX-ACCESS    read-only
        STATUS        current
        DESCRIPTION   "The  round trip time of the current packet that
                      have been sent in this sequence."
        ::= { traceRouteDataEntry 4 }

traceRouteDataHopCount OBJECT-TYPE
        SYNTAX        INTEGER(1..65535)
        MAX-ACCESS    read-only
        STATUS        current
        DESCRIPTION   "The number of hop starting from the place where
                      the traceroute operation is initialized to the
                      gateway which has the traceRouteDataGatewayIp."
        ::= { traceRouteDataEntry 5 }

traceRouteDataErrors OBJECT-TYPE
        SYNTAX        INTEGER {
                        icmpUnreachNet(1),      -- bad net
                        icmpUnreachHost(2),     -- bad host
                        icmpUnreachProtocol(3), -- bad protocol
                        icmpUnreachPort(4),     -- bad port
                        icmpUnreachNeedFrag(5), -- IP defragment caused
                                                -- drop
                        icmpUnreachSrcFail(6),  -- src route failed
                        icmpUnreachNoNet(7),    -- no such network
                        icmpUnreachNoHost(8),   -- no such host
                        icmpUnreachHostIsolated(9), -- host isolated
                        icmpUnreachNetProhib(10),
                                          -- dod net admin prohibited
                        icmpUnreachProhib(11),
                                          -- dod host admin prohibit
                        icmpUnreachNetTos(12),
                                          -- net and tos unreachable
                        icmpUnreachHostTos(13),
                                          -- host and tos unreachable
                        icmpUnreachAdmin(14),
                                          -- administratively prohibited
                        icmpUnreachHostPrec(15), -- host precedence
                        icmpUnreachPrecedence(16), -- precedence cutoff
                        icmpUnknown(17),        -- unknown error
                        icmpTimeOut(18),        -- time out
                        icmpTTLExpired(19)      -- ttl expired
                      }
        MAX-ACCESS    read-only
        STATUS        current
        DESCRIPTION   "The error of the traceroute operation."
        ::= { traceRouteDataEntry 6 }



-- the fileCopy group

-- Implementation of the file group is current for all Cisco Workgroup
-- Stack products which implement tftp/rcp upload/download functions
-- or local file copy.

fileCopyProtocol OBJECT-TYPE
        SYNTAX        INTEGER { tftp (1),
                                rcp (2)
                              }
        MAX-ACCESS    read-write
        STATUS        current
        DESCRIPTION   "The protocol to be used for any remote copy.
                      If the config file transfer is to occur locally on
                      the SNMP agent, the method of transfer is left up
                      to the implementation, and is not restricted to
                      the protocols above.

                      The value of this object can not be changed when
                      the fileCopyResult object has the value of
                      inProgress(1)."
        DEFVAL { tftp }
        ::= { fileCopyGrp 1 }

fileCopyRemoteServer OBJECT-TYPE
        SYNTAX        DisplayString (SIZE (0..64))
        MAX-ACCESS    read-write
        STATUS        current
        DESCRIPTION   "The IP address  or the host name of the tftp/rcp
                      remote server from (or to) which to copy the file.
                      If the copy operation  is local on the SNMP agent,
                      this object is not applicable.

                      The value of this object can not be changed when
                      the fileCopyResult object has the value of
                      inProgress(1)."
        ::= { fileCopyGrp 2 }

fileCopySrcFileName OBJECT-TYPE
        SYNTAX        DisplayString (SIZE (0..64))
        MAX-ACCESS    read-write
        STATUS        current
        DESCRIPTION   "The source file name (including the path, if
                      applicable) of the file. The accepted value of
                      this object is 'cfg1' or 'cfg2' when the requested
                      action is one of the following:

                      copyConfigFromFlashToRuntime(8), and
                      copyConfigFileFromFlashToHost(11).

                      The value of this object can not be changed when
                      the fileCopyResult object has the value of
                      inProgress(1)."
        ::= { fileCopyGrp 3 }

fileCopyDstFileName OBJECT-TYPE
        SYNTAX        DisplayString (SIZE (0..64))
        MAX-ACCESS    read-write
        STATUS        current
        DESCRIPTION   "The destination file name (including the path, if
                      applicable) of the file. The accepted value of
                      this object is 'cfg1' or 'cfg2' when the requested
                      action is one of the following:

                      copyConfigFromRuntimeToFlash(9),
                      copyConfigFileFromHostToFlash(10).

                      The value of this object can not be changed when
                      the fileCopyResult object has the value of
                      inProgress(1)."
        ::= { fileCopyGrp 4 }

fileCopyModuleNumber OBJECT-TYPE
        SYNTAX        INTEGER(0..16)
        MAX-ACCESS    read-write
        STATUS        current
        DESCRIPTION   "The module number specified in the copy
                      operation.

                      If the value of this object is 0 and the
                      fileCopyAction object has the value of
                      copyImageFromHostToFlash(4), the switch will do
                      multiple download to the modules with matching
                      image type. It is left to the SNMP agent to allow
                      the individual modules to be reset with the
                      downloaded images or not.

                      The value of this object can not be changed when
                      the fileCopyResult object has the value of
                      inProgress(1)."
        ::= { fileCopyGrp 5 }

fileCopyUserName OBJECT-TYPE
        SYNTAX        DisplayString(SIZE (1..40))
        MAX-ACCESS    read-write
        STATUS        current
        DESCRIPTION   "Remote user name for copy via rcp protocol. This
                      object must be specified when the
                      fileCopyProtocol is rcp."
        ::= { fileCopyGrp 6 }

fileCopyAction OBJECT-TYPE
        SYNTAX        INTEGER {
                                other(1),       -- none of the following
                                copyConfigFromHostToRuntime(2),
                                copyConfigFromRuntimeToHost(3),
                                copyImageFromHostToFlash(4),
                                copyImageFromFlashToHost(5),
                                copyConfigFromFlashToRuntime(8),
                                copyConfigFromRuntimeToFlash(9),
                                copyConfigFileFromHostToFlash(10),
                                copyConfigFileFromFlashToHost(11),
                                copyTechReportFromRuntimeToHost(12)
                              }
        MAX-ACCESS    read-write
        STATUS        current
        DESCRIPTION   "Setting this object to one of the acceptable
                      values will initiate the requested action using
                      the information provided by fileCopyProtocol,
                      fileCopyRemoteServer, fileCopySrcFileName,
                      fileCopyDstFileName,fileCopyModuleNumber and
                      fileCopyUserName.

                      copyConfigFromHostToRuntime(2):
                         Copy the configuration file from host to
                         runtime configuration over the network through
                         tftp/rcp. This action will use
                         fileCopyProtocol, fileCopyRemoteServer,
                         fileCopySrcFileName, fileCopyModuleNumber,
                         and fileCopyUserName (if applicable).

                      copyConfigFromRuntimeToHost(3):
                         Copy the runtime configuration to host over the
                         network through tftp/rcp. This action will use
                         fileCopyProtocol, fileCopyRemoteServer,
                         fileCopyModuleNumber, fileCopyDstFileName,
                         fileCopyUserName (if applicable), and
                         fileCopyRuntimeConfigPart.

                      copyImageFromHostToFlash(4):
                         Copy the image from host to the flash over the
                         network through tftp/rcp. It is up to the
                         SNMP agent to reset and run the downloaded
                         image after copying. This action will use
                         fileCopyProtocol, fileCopyRemoteServer,
                         fileCopySrcFileName, fileCopyModuleNumber,
                         and fileCopyUserName (if applicable).

                      copyImageFromFlashToHost(5):
                         Copy the image from flash to host over the
                         switch through tftp/rcp. This action will use
                         fileCopyProtocol, fileCopyRemoteServer,
                         fileCopyDstFileName, fileCopyModuleNumber,
                         and fileCopyUserName (if applicable).

                      copyConfigFromFlashToRuntime(8):
                         Copy the configuration file to the runtime
                         configuration locally. This action can perform
                         only on the SUPG supervisor model and will
                         use fileCopySrcFileName ('cfg1' or 'cfg2').

                      copyConfigFromRuntimeToFlash(9):
                         Copy  the runtime configuration to a
                         configuration file on the flash locally. This
                         action can perform only on the SUPG supervisor
                         model and will use fileCopyDstFileName ('cfg1'
                         or 'cfg2'), and fileCopyRuntimeConfigPart.

                      copyConfigFileFromHostToFlash(10):
                         Copy the configuration file from host to the
                         runtime configuration over the network through
                         tftp/rcp. This action can perform only on the
                         SUPG  supervisor model and will use
                         fileCopyProtocol, fileCopyRemoteServer,
                         fileCopySrcFileName, fileCopyDstFileName,
                         fileCopyModuleNumber and fileCopyUserName
                         (if applicable).

                      copyConfigFileFromFlashToHost(11):
                         Copy the configuration file on the flash to
                         host over the network through tftp/rcp.
                         This action can perform only on the
                         SUPG supervisor model and will use
                         fileCopyProtocol, fileCopyRemoteServer,
                         fileCopySrcFileName, fileCopyDstFileName,
                         fileCopyModuleNumber and fileCopyUserName
                         (if applicable).

                      copyTechReportFromRuntimeToHost(12):
                         Copy the technical report of the system to
                         host over the network through tftp only. This
                         action will use fileCopyProtocol,
                         fileCopyRemoteServer, fileCopyModuleNumber,
                         and fileCopyDstFileName.

                      Setting this object to any other value results in
                      an error.

                      The value of this object can not be changed when
                      the fileCopyResult object has the value of
                      inProgress(1)."
        ::= { fileCopyGrp 7 }

fileCopyResult OBJECT-TYPE
        SYNTAX        INTEGER {
                                inProgress(1),
                                success(2),
                                noResponse(3),
                                tooManyRetries(4),
                                noBuffers(5),
                                noProcesses(6),
                                badChecksum(7),
                                badLength(8),
                                badFlash(9),
                                serverError(10),
                                userCanceled(11),
                                wrongCode(12),
                                fileNotFound(13),
                                invalidHost(14),
                                invalidModule(15),
                                accessViolation(16),
                                unknownStatus(17),
                                invalidStorageDevice(18),
                                insufficientSpaceOnStorageDevice(19),
                                insufficientDramSize(20),
                                incompatibleImage(21),
                                rcpError(22)
                              }
        MAX-ACCESS    read-only
        STATUS        current
        DESCRIPTION   "Contains the result of the last copy action
                      request.
                      If the value of fileCopyResult is rcpError(22),
                      then the detailed rcp error messages are contained
                      in fileCopyResultRcpErrorMessage."
         ::= { fileCopyGrp 8 }

fileCopyResultRcpErrorMessage OBJECT-TYPE
        SYNTAX        DisplayString (SIZE (0..255))
        MAX-ACCESS    read-only
        STATUS        current
        DESCRIPTION   "Contains the detailed rcp error messages if the
                      value of fileCopyResult is rcpError(22) for the
                      last copy action request; otherwise, this MIB
                      object contains the empty string."
        ::= { fileCopyGrp 9 }

fileCopyRuntimeConfigPart OBJECT-TYPE
        SYNTAX        INTEGER {
                               all(1),
                               nonDefault(2)
                              }
        MAX-ACCESS    read-write
        STATUS        current
        DESCRIPTION   "Indicates the part of runtime configuration to be
                      copied. This object will only take effect when the
                      object value of fileCopyAction is one of the
                      following:

                      copyConfigFromRuntimeToHost(3),
                      copyConfigFromRuntimeToFlash(9).

                      all -- copy all the runtime configuration.

                      nonDefault --copy only the part of the runtime
                                   configuration which is different from
                                   the default configuration."
        DEFVAL        { all }
        ::= { fileCopyGrp 10 }


-- The voice Group
-- Voice Port Interface Configuration Table

voicePortIfConfigTable OBJECT-TYPE
        SYNTAX        SEQUENCE OF VoicePortIfConfigEntry
        MAX-ACCESS    not-accessible
        STATUS        current
        DESCRIPTION   "A list of port entries. The number of entries is
                      determined by the number of modules in the chassis
                      and the number of ports with the voice port
                      interface configuration capability in the system."
        ::= { voiceGrp 1 }

voicePortIfConfigEntry OBJECT-TYPE
        SYNTAX        VoicePortIfConfigEntry
        MAX-ACCESS    not-accessible
        STATUS        current
        DESCRIPTION   "Entry containing voice interface configuration
                      for a particular port."
        INDEX         { voicePortIfConfigModuleIndex,
                        voicePortIfConfigPortIndex }
        ::= { voicePortIfConfigTable 1 }

VoicePortIfConfigEntry ::=
        SEQUENCE {
                voicePortIfConfigModuleIndex      INTEGER,
                voicePortIfConfigPortIndex        INTEGER,
                voicePortIfDHCPEnabled            TruthValue,
                voicePortIfIpAddress              IpAddress,
                voicePortIfIpNetMask              IpAddress,
                voicePortIfTftpServerAddress      IpAddress,
                voicePortIfGatewayAddress         IpAddress,
                voicePortIfDnsServerAddress       IpAddress,
                voicePortIfDnsDomain              DisplayString,
                voicePortIfOperDnsDomain          DisplayString
        }

voicePortIfConfigModuleIndex OBJECT-TYPE
        SYNTAX        INTEGER (1..16)
        MAX-ACCESS    not-accessible
        STATUS        current
        DESCRIPTION   "An index value that uniquely identifies the
                      module where this port is located."
        ::= { voicePortIfConfigEntry 1 }

voicePortIfConfigPortIndex OBJECT-TYPE
        SYNTAX        INTEGER (1..255)
        MAX-ACCESS    not-accessible
        STATUS        current
        DESCRIPTION   "An index value that uniquely identifies this port
                      within a module. The value is determined by the
                      location of the port on the module."
        ::= { voicePortIfConfigEntry 2 }

voicePortIfDHCPEnabled OBJECT-TYPE
        SYNTAX        TruthValue
        MAX-ACCESS    read-write
        STATUS        current
        DESCRIPTION   "Indicate whether DHCP service is enabled."
        DEFVAL { true }
        ::= { voicePortIfConfigEntry 3 }

voicePortIfIpAddress OBJECT-TYPE
        SYNTAX        IpAddress
        MAX-ACCESS    read-write
        STATUS        current
        DESCRIPTION   "This port's IP address. This object
                      is configurable only if voicePortIfDHCPEnabled
                      is false. When the value of voicePortIfDHCPEnabled
                      is false, this object should be configured."
        ::= { voicePortIfConfigEntry 4 }

voicePortIfIpNetMask OBJECT-TYPE
        SYNTAX        IpAddress
        MAX-ACCESS    read-write
        STATUS        current
        DESCRIPTION   "This port's subnet mask. This object
                      is configurable only if voicePortIfDHCPEnabled
                      is false. When the value of voicePortIfDHCPEnabled
                      is false, this object should be configured."
        ::= { voicePortIfConfigEntry 5 }

voicePortIfTftpServerAddress OBJECT-TYPE
        SYNTAX        IpAddress
        MAX-ACCESS    read-write
        STATUS        current
        DESCRIPTION   "This port's TFTP Server address. This object
                      is configurable only if voicePortIfDHCPEnabled
                      is false. When the value of voicePortIfDHCPEnabled
                      is false, this object should be configured."
        ::= { voicePortIfConfigEntry 6 }

voicePortIfGatewayAddress OBJECT-TYPE
        SYNTAX        IpAddress
        MAX-ACCESS    read-write
        STATUS        current
        DESCRIPTION   "This port's router address. This object
                      is configurable only if voicePortIfDHCPEnabled
                      is false."
        ::= { voicePortIfConfigEntry 7 }

voicePortIfDnsServerAddress OBJECT-TYPE
        SYNTAX        IpAddress
        MAX-ACCESS    read-write
        STATUS        current
        DESCRIPTION   "This port's DNS Server address. This object
                      is configurable only if voicePortIfDHCPEnabled
                      is false."
        ::= { voicePortIfConfigEntry 8 }

voicePortIfDnsDomain OBJECT-TYPE
        SYNTAX        DisplayString (SIZE (0..255))
        MAX-ACCESS    read-write
        STATUS        current
        DESCRIPTION   "This port's DNS domain name. This object
                      is configurable only if voicePortIfDHCPEnabled
                      is false."
        ::= { voicePortIfConfigEntry 9 }

voicePortIfOperDnsDomain OBJECT-TYPE
        SYNTAX        DisplayString (SIZE (0..255))
        MAX-ACCESS    read-only
        STATUS        current
        DESCRIPTION   "This port's operational DNS domain name. If
                      voicePortIfDHCPEnabled is true, this object
                      indicates the domain name taken from the
                      DHCP server. If voicePortIfDHCPEnabled is false,
                      this object indicates the domain name configured
                      by users for this voice port or the domain name
                      taken from DNS configuration for the system
                      otherwise."
        ::= { voicePortIfConfigEntry 10 }


-- Voice Port Call Manager Table
voicePortCallManagerTable OBJECT-TYPE
        SYNTAX        SEQUENCE OF VoicePortCallManagerEntry
        MAX-ACCESS    not-accessible
        STATUS        current
        DESCRIPTION   "A list of call manager entries. The number of
                      entries is determined by the number of modules in
                      the chassis and the number of ports with the
                      voice port interface configuration capability
                      in the system."
        ::= { voiceGrp 2 }

voicePortCallManagerEntry OBJECT-TYPE
        SYNTAX        VoicePortCallManagerEntry
        MAX-ACCESS    not-accessible
        STATUS        current
        DESCRIPTION   "Entry containing voice interface configuration
                      for a particular port."
        INDEX         { voicePortModuleIndex, voicePortIndex,
                        voicePortCallManagerIndex }
        ::= { voicePortCallManagerTable 1 }

VoicePortCallManagerEntry ::=
        SEQUENCE {
                voicePortModuleIndex
                        INTEGER,
                voicePortIndex
                        INTEGER,
                voicePortCallManagerIndex
                        INTEGER,
                voicePortCallManagerIpAddr
                        IpAddress
                }

voicePortModuleIndex OBJECT-TYPE
        SYNTAX        INTEGER(1..16)
        MAX-ACCESS    not-accessible
        STATUS        current
        DESCRIPTION   "An index value that uniquely identifies the
                      module where this port is located."
        ::= { voicePortCallManagerEntry 1 }

voicePortIndex OBJECT-TYPE
        SYNTAX        INTEGER (1..255)
        MAX-ACCESS    not-accessible
        STATUS        current
        DESCRIPTION   "An index value that uniquely identifies this port
                      within a module."
        ::= { voicePortCallManagerEntry 2 }

voicePortCallManagerIndex OBJECT-TYPE
        SYNTAX        INTEGER (1..5)
        MAX-ACCESS    not-accessible
        STATUS        current
        DESCRIPTION   "An index value that uniquely identifies this
                      CallManager within a module/port. A port can
                      register up to 5 CallManager."
        ::= { voicePortCallManagerEntry 3 }

voicePortCallManagerIpAddr OBJECT-TYPE
        SYNTAX        IpAddress
        MAX-ACCESS    read-only
        STATUS        current
        DESCRIPTION   "The Call Manager IP Address of this port. A port
                      can register up to 5 call managers."
        ::= { voicePortCallManagerEntry 4 }

-- Voice Port Operational Dns Server Table

voicePortOperDnsServerTable OBJECT-TYPE
        SYNTAX        SEQUENCE OF VoicePortOperDnsServerEntry
        MAX-ACCESS    not-accessible
        STATUS        current
        DESCRIPTION   "A list of operational DNS entries used by the
                      voice ports."
        ::= { voiceGrp 3 }

voicePortOperDnsServerEntry OBJECT-TYPE
        SYNTAX        VoicePortOperDnsServerEntry
        MAX-ACCESS    not-accessible
        STATUS        current
        DESCRIPTION   "Entry containing infomation on DNS servers may be
                      used for a particular voice port.

                      If DHCP is enabled on a port, the DNS server IP
                      address will come from the DHCP server. If DHCP
                      is disabled, the DNS server IP address can be
                      configured by users through the mib object
                      voicePortIfDnsServerAddress for a port, otherwise
                      it will be taken from DNS configuration in the
                      system."
        INDEX         { voicePortDnsModuleIndex, voicePortDnsPortIndex,
                        voicePortOperDnsServerIndex }
        ::= { voicePortOperDnsServerTable 1 }

VoicePortOperDnsServerEntry ::=
        SEQUENCE {
                voicePortDnsModuleIndex
                        INTEGER,
                voicePortDnsPortIndex
                        INTEGER,
                voicePortOperDnsServerIndex
                        Unsigned32,
                voicePortOperDnsServerIpAddr
                        IpAddress,
                voicePortOperDnsServerSource
                        INTEGER
                }

voicePortDnsModuleIndex OBJECT-TYPE
        SYNTAX        INTEGER(1..16)
        MAX-ACCESS    not-accessible
        STATUS        current
        DESCRIPTION   "An index value that uniquely identifies the
                      module where this port is located."
        ::= { voicePortOperDnsServerEntry 1 }

voicePortDnsPortIndex OBJECT-TYPE
        SYNTAX        INTEGER (1..255)
        MAX-ACCESS    not-accessible
        STATUS        current
        DESCRIPTION   "An index value that uniquely identifies this port
                       within a module."
        ::= { voicePortOperDnsServerEntry 2 }

voicePortOperDnsServerIndex OBJECT-TYPE
        SYNTAX        Unsigned32
        MAX-ACCESS    not-accessible
        STATUS        current
        DESCRIPTION   "An index value that uniquely identifies this DNS
                       server within a module/port. This value indicates
                       the priority order among these DNS servers."
        ::= { voicePortOperDnsServerEntry 3 }

voicePortOperDnsServerIpAddr OBJECT-TYPE
        SYNTAX        IpAddress
        MAX-ACCESS    read-only
        STATUS        current
        DESCRIPTION   "The operational DNS Server IP Address of this
                      port. "
        ::= { voicePortOperDnsServerEntry 4 }

voicePortOperDnsServerSource OBJECT-TYPE
        SYNTAX        INTEGER {
                           fromDhcp (1),
                           fromPortConfig (2),
                           fromSystemConfig (3)
                      }
        MAX-ACCESS    read-only
        STATUS        current
        DESCRIPTION   "The source of the Dns Server IP Address of this
                      port.

                      fromDhcp(1) indicates that the DNS server IP
                      address comes from the DHCP server.

                      fromPortConfig(2) indicates that the DNS server IP
                      address comes from the object
                      voicePorfIfDnsServerAdress.

                      fromSystemConfig(3) indicates that the DNS server
                      IP address comes from DNS configuration for the
                      system."
        ::= { voicePortOperDnsServerEntry 5 }



-- the port jumbo frame group
-- If the port jumbo frame feature is supported, this
-- portJumboFrameTable
-- should be implemented.

portJumboFrameTable OBJECT-TYPE
        SYNTAX        SEQUENCE OF PortJumboFrameEntry
        MAX-ACCESS    not-accessible
        STATUS        current
        DESCRIPTION   "A list of port jumbo frame entries. The number of
                      entries is determined by the number of ports in
                      the system which support the Jumbo frame feature."
        ::= { portJumboFrameGrp 1}


portJumboFrameEntry OBJECT-TYPE
        SYNTAX        PortJumboFrameEntry
        MAX-ACCESS    not-accessible
        STATUS        current
        DESCRIPTION   "Entry containing the jumbo frame configuration
                      for a particular port."
        INDEX         { portJumboFrameModuleIndex,
                        portJumboFramePortIndex }
        ::= { portJumboFrameTable 1 }

PortJumboFrameEntry ::=
        SEQUENCE {
                portJumboFrameModuleIndex
                        INTEGER,
                portJumboFramePortIndex
                        INTEGER,
                portJumboFrameEnable
                        INTEGER
        }

portJumboFrameModuleIndex OBJECT-TYPE
        SYNTAX        INTEGER (1..16)
        MAX-ACCESS    read-only
        STATUS        current
        DESCRIPTION   "An index value that uniquely identifies the
                      module where this port is located."
        ::= { portJumboFrameEntry 1 }

portJumboFramePortIndex OBJECT-TYPE
        SYNTAX        INTEGER (1..255)
        MAX-ACCESS    read-only
        STATUS        current
        DESCRIPTION   "An index value that uniquely identifies this port
                      within a module. The value is determined by the
                      location of the port on the module. Valid entries
                      are 1 to the value of moduleNumPorts for this
                      module."
        ::= { portJumboFrameEntry 2 }

portJumboFrameEnable OBJECT-TYPE
        SYNTAX  INTEGER {
                      enabled(1),
                      disabled(2)
                }
        MAX-ACCESS    read-write
        STATUS        current
        DESCRIPTION   "Indicates the jumbo frame status of the port. If
                      enabled, the port supports frame size greater than
                      the standard ethernet frame size of 1518 bytes."
        ::= { portJumboFrameEntry 3 }



-- the switch acceleration group

-- If the module switch acceleration feature is supported, the
-- switchAccelerationModuleTable should be implemented.

switchAccelerationModuleTable OBJECT-TYPE
        SYNTAX        SEQUENCE OF SwitchAccelerationModuleEntry
        MAX-ACCESS    not-accessible
        STATUS        current
        DESCRIPTION   "This table contains a list of the modules for
                      which the switch acceleration capability can be
                      configured."
        ::= { switchAccelerationGrp 1 }

switchAccelerationModuleEntry OBJECT-TYPE
        SYNTAX        SwitchAccelerationModuleEntry
        MAX-ACCESS    not-accessible
        STATUS        current
        DESCRIPTION   "A module for which switch acceleration can be
                      configured."
        INDEX         { switchAccelerationModuleIndex }
        ::= { switchAccelerationModuleTable 1 }

SwitchAccelerationModuleEntry ::=
        SEQUENCE {
                switchAccelerationModuleIndex
                        INTEGER,
                switchAccelerationModuleEnable
                        TruthValue
        }

switchAccelerationModuleIndex OBJECT-TYPE
        SYNTAX        INTEGER (1..16)
        MAX-ACCESS    read-only
        STATUS        current
        DESCRIPTION   "The value of moduleIndex for the module where
                      switch acceleration feature can be configured."
        ::= {switchAccelerationModuleEntry  1 }

switchAccelerationModuleEnable OBJECT-TYPE
        SYNTAX        TruthValue
        MAX-ACCESS    read-write
        STATUS        current
        DESCRIPTION   "Indicates whether switch acceleration is enabled
                     on  this module or not.

                      When this feature is enabled, the system will
                      increase the switching bandwidth, but the
                      ifAdminStatus of any port on this module can not
                      be set to 'up'.

                      If the ifAdminStatus of any port on this module is
                      'up', this feature can not be enabled until
                      ifAdminStatus of all ports on the module is set
                      to 'down'."
        DEFVAL { false }
        ::= {switchAccelerationModuleEntry  2 }

-- The configuration Group

configMode            OBJECT-TYPE
        SYNTAX        INTEGER {
                               binary(1),   -- binary mode
                               text(2)      -- text mode
                              }
        MAX-ACCESS    read-write
        STATUS        current
        DESCRIPTION   "Configuration mode to store the configuration
                      information."
        DEFVAL { binary }
        ::= { configGrp 1 }

configTextFileLocation     OBJECT-TYPE
        SYNTAX        DisplayString (SIZE (0..255))
        MAX-ACCESS    read-write
        STATUS        current
        DESCRIPTION   "The location of the text configuration file
                      which can be either NVRAM or a file in the
                      FLASH file system. If the location is NVRAM,
                      this object is a zero length octet string.
                      Otherwise, the FLASH file should be specified
                      in <device>:<filename> format. This object
                      is only instantiated when configMode has
                      the value of of text(2). "
        DEFVAL {''H }
        ::= { configGrp 2 }

configWriteMem        OBJECT-TYPE
        SYNTAX        TruthValue
        MAX-ACCESS    read-write
        STATUS        current
        DESCRIPTION   "When this object is set to true(1), the current
                      configuration is saved in text format in the
                      location specified by configTextFileLocation.
                      This object is only instantiated when configMode
                      has the value of text(2). When read,
                      this object always returns false(2). "
        ::= { configGrp 3 }

configWriteMemStatus  OBJECT-TYPE
        SYNTAX        INTEGER {
                        inProgress(1),
                        succeeded(2),
                        resourceUnavailable(3),
                        badFileName(4),
                        someOtherError(5)
                              }
        MAX-ACCESS    read-write
        STATUS        current
        DESCRIPTION   "The status of the current or the most recently
                      completed 'write memory' operation. The possible
                      values are:

                        inProgress - 'write' operation in progress;

                        succeeded - the 'write' was successful (this
                        value is also used when no write has been
                        invoked since the last time the local system
                        restarted);

                        resourceUnavailable, -the 'write' failed because
                        insufficeient resource was available.

                        badFileName - the 'write' failed because the
                        specified destination file was not found.
                        This might be due to invalid FLASH device
                        name or invalid file name.

                        someOtherError - the 'write' failed for some
                        other reason.

                     This object is only instantiated when configMode
                     has the value of text(2). "
       ::= { configGrp 4 }

-- traps

ciscoStackNotificationsPrefix OBJECT IDENTIFIER ::= { workgroup 0 }

lerAlarmOn NOTIFICATION-TYPE
        OBJECTS       { fddimibPORTSMTIndex, fddimibPORTIndex }
        STATUS        current
        DESCRIPTION   "A lerAlarmOn trap signifies that the agent entity
                      has detected that the fddimibPORTLerFlag object in
                      the FDDI-SMT73-MIB (RFC 1512) has transitioned to
                      the true(1) state for one of its ports.
                      The generation of this trap can be controlled by
                      the fddimibPORTLerAlarm object in the
                      FDDI-SMT73-MIB for each port."
        ::= { ciscoStackNotificationsPrefix 1}

lerAlarmOff NOTIFICATION-TYPE
        OBJECTS       { fddimibPORTSMTIndex, fddimibPORTIndex }
        STATUS        current
        DESCRIPTION   "A lerAlarmOff trap signifies that the agent
                      entity has detected that the fddimibPORTLerFlag
                      object in the FDDI-SMT73-MIB (RFC 1512) has
                      transitioned to the false(2) state for one of
                      its ports. The generation of this trap can be
                      controlled by the fddimibPORTLerAlarm object in
                      the FDDI-SMT73-MIB for each port."
        ::= { ciscoStackNotificationsPrefix 2}

moduleUp NOTIFICATION-TYPE
        OBJECTS       { moduleIndex, moduleType }
        STATUS        current
        DESCRIPTION   "A moduleUp trap signifies that the agent entity
                      has detected that the moduleStatus object in this
                      MIB has transitioned to the ok(2) state for one of
                      its modules.
                      The generation of this trap can be controlled by
                      the sysEnableModuleTraps object in this MIB."
        ::= { ciscoStackNotificationsPrefix 3}

moduleDown NOTIFICATION-TYPE
        OBJECTS       { moduleIndex, moduleType }
        STATUS        current
        DESCRIPTION   "A moduleDown trap signifies that the agent entity
                      has detected that the moduleStatus object in this
                      MIB has transitioned out of the ok(2) state for
                      one of its modules.
                      The generation of this trap can be controlled by
                      the sysEnableModuleTraps object in this MIB."
        ::= { ciscoStackNotificationsPrefix 4}

chassisAlarmOn NOTIFICATION-TYPE
        OBJECTS       { chassisTempAlarm, chassisMinorAlarm,
                        chassisMajorAlarm }
        STATUS        current
        DESCRIPTION   "A chassisAlarmOn trap signifies that the agent
                      entity has detected the chassisTempAlarm,
                      chassisMinorAlarm, or chassisMajorAlarm object in
                      this MIB has transitioned to the on(2) state.
                      The generation of this trap can be controlled by
                      the sysEnableChassisTraps object in this MIB."
        ::= { ciscoStackNotificationsPrefix 5}

chassisAlarmOff NOTIFICATION-TYPE
        OBJECTS       { chassisTempAlarm, chassisMinorAlarm,
                        chassisMajorAlarm }
        STATUS        current
        DESCRIPTION   "A chassisAlarmOff trap signifies that the agent
                      entity has detected the chassisTempAlarm,
                      chassisMinorAlarm, or chassisMajorAlarm object in
                      this MIB has transitioned to the off(1) state.
                      The generation of this trap can be controlled by
                      the sysEnableChassisTraps object in this MIB."
        ::= { ciscoStackNotificationsPrefix 6}

ipPermitDeniedTrap NOTIFICATION-TYPE
        OBJECTS       { ipPermitDeniedAddress, ipPermitDeniedAccess }
        STATUS        current
        DESCRIPTION   "ipPermitDeniedTrap indicates that IP permit
                      denied access happens. The generation of this
                      trap can be controlled by the
                      sysEnableIpPermitTraps object in this MIB."
        ::= { ciscoStackNotificationsPrefix 7}

sysConfigChangeTrap NOTIFICATION-TYPE
        OBJECTS       { sysConfigChangeTime, sysConfigChangeInfo }
        STATUS        current
        DESCRIPTION   "A sysConfigChange trap signifies that the system
                      configuration in NVRAM is changed. The generation
                      of this trap can be controlled by the
                      sysEnableConfigTraps object in this MIB."
        ::= { ciscoStackNotificationsPrefix 9 }

tokenRingSoftErrExceededTrap NOTIFICATION-TYPE
        OBJECTS      { ringStationMacAddress, ifIndex, ifName }
        STATUS             current
        DESCRIPTION  "This trap is generated when a station local to a
                      token ring port exceeds its Soft Error Threshold
                      within the configured interval."
        ::= { ciscoStackNotificationsPrefix 10 }


-- conformance information

ciscoStackMIBConformance OBJECT IDENTIFIER ::= { ciscoStackMIB 31 }
ciscoStackMIBCompliances OBJECT IDENTIFIER ::=
                                { ciscoStackMIBConformance 1 }
ciscoStackMIBGroups      OBJECT IDENTIFIER ::=
                                { ciscoStackMIBConformance 2 }

-- compliance statements

ciscoStackgMIBCompliance MODULE-COMPLIANCE
        STATUS        deprecated
        DESCRIPTION   "The compliance statement for entities which
                       implement the Cisco stack MIB."
        MODULE        -- this module
        MANDATORY-GROUPS {
                systemMiscGroup,
                systemTrapGroup,
                chassisGroup,
                moduleGroup,
                portGroup
        }
        GROUP optionalSystemMiscGroup
        DESCRIPTION   "The OptionalSystemMiscGroup is an optional group
                       containing objects  providing information about
                       the miscellaneous system features."
        GROUP optionalSystemTrapGroup
        DESCRIPTION   "The OptionalSystemTrapGroup is an optional group
                      containing objects providing information about
                      the SNMP traps feature."
        GROUP optionalChassisGroup
        DESCRIPTION   "The OptionalChassisGroup is an optional group
                      containing objects providing information about the
                      chassis of the device."
        GROUP optionalModuleGroup
        DESCRIPTION   "The OptionalMooduleGroup is an optional group
                      containing objects providing information about the
                      modules on the device."
        GROUP optionalPortGroup
        DESCRIPTION   "The OptionalPortGroup is an optional group
                      containing objects providing information about the
                      ports on the device."
        GROUP systemTrafficGroup
        DESCRIPTION   "The systemTrafficGroup is an optional group
                      containing objects providing information about the
                      traffic meter feature."
        GROUP systemFddiGroup
        DESCRIPTION   "The systemFddiGroup is an optional group
                      containing objects providing information about the
                      FDDI ring feature."
        GROUP systemRmonGroup
        DESCRIPTION   "The systemRmonGroup is an optional group
                      containing objects providing information about the
                      extended RMON feature."
        GROUP authenticationGroup
        DESCRIPTION   "The authenticationGroup is an optional group
                      containing objects providing information about
                      the authentication features."
        GROUP tftpGroup
        DESCRIPTION   "The tftpGroup is an optional group containing
                      objects providing information about the tftp
                      upload/download features."
        GROUP brouteEnableGroup
        DESCRIPTION   "The brouteEnableGroup is an optional group
                      containing objects providing information about the
                      combined bridging/routing feature."
        GROUP filterGroup
        DESCRIPTION   "The filterGroup is an optional group containing
                      objects providing information about the port
                      filtering feature."
        GROUP monitorGroup
        DESCRIPTION   "The monitorGroup is an optional group containing
                      objects providing information about the port
                      monitoring feature, also known as the Switched
                      Port ANalyzer (SPAN) feature."
        GROUP vlanGroup
        DESCRIPTION   "The vlanGroup is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects  providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup
        DESCRIPTION   "The ipPermitGroup is an optional group containing
                      objects providing information about the ip permit
                      list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                      objects providing information about the tftp/rcp
                      or local file upload/download features."
        GROUP optionalSystemMiscGroup1
        DESCRIPTION   "The optionalSystemMiscGroup1 is an optional group
                      containing objects providing information about the
                      miscellaneous system features."
        ::= { ciscoStackMIBCompliances 1 }

ciscoStackgMIBCompliance2 MODULE-COMPLIANCE
        STATUS        deprecated
        DESCRIPTION   "The compliance statement for entities which
                      implement the Cisco stack MIB."
        MODULE        -- this module
        MANDATORY-GROUPS {
                systemMiscGroup,
                systemTrapGroup,
                chassisGroup,
                moduleGroup,
                portGroup
        }
        GROUP optionalSystemMiscGroup
        DESCRIPTION   "The OptionalSystemMiscGroup is an optional group
                      containing objects  providing information about
                      the miscellaneous system features."
        GROUP optionalSystemTrapGroup
        DESCRIPTION   "The OptionalSystemTrapGroup is an optional group
                      containing objects providing information about the
                      SNMP traps feature."
        GROUP optionalChassisGroup
        DESCRIPTION   "The OptionalChassisGroup is an optional group
                      containing objects providing information about the
                      chassis of the device."
        GROUP optionalModuleGroup
        DESCRIPTION   "The OptionalMooduleGroup is an optional group
                      containing objects providing information about the
                      modules on the device."
        GROUP optionalPortGroup
        DESCRIPTION   "The OptionalPortGroup is an optional group
                      containing objects providing information about the
                      ports on the device."
        GROUP systemTrafficGroup
        DESCRIPTION   "The systemTrafficGroup is an optional group
                      containing objects providing information about the
                      traffic meter feature."
        GROUP systemFddiGroup
        DESCRIPTION   "The systemFddiGroup is an optional group
                      containing objects providing information about the
                      FDDI ring feature."
        GROUP systemRmonGroup
        DESCRIPTION   "The systemRmonGroup is an optional group
                      containing objects providing information about
                      the extended RMON feature."
        GROUP authenticationGroup
        DESCRIPTION   "The authenticationGroup is an optional group
                      containing objects providing information about
                      the authentication features."
        GROUP tftpGroup
        DESCRIPTION   "The tftpGroup is an optional group containing
                      objects providing information about the tftp
                      upload/download features."
        GROUP brouteEnableGroup
        DESCRIPTION   "The brouteEnableGroup is an optional group
                      containing objects providing information about
                      the combined bridging/routing feature."
        GROUP filterGroup
        DESCRIPTION   "The filterGroup is an optional group containing
                      objects providing information about the port
                      filtering feature."
        GROUP monitorGroup
        DESCRIPTION   "The monitorGroup is an optional group containing
                      objects providing information about the port
                      monitoring feature, also known as the Switched
                      Port ANalyzer (SPAN) feature."
        GROUP vlanGroup
        DESCRIPTION   "The vlanGroup is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects  providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup
        DESCRIPTION   "The ipPermitGroup is an optional group containing
                      objects providing information about the ip permit
                      list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                      objects providing information about the tftp/rcp
                      or local file upload/download features."
        GROUP optionalSystemMiscGroup1
        DESCRIPTION   "The optionalSystemMiscGroup1 is an optional group
                      containing objects providing information about the
                      miscellaneous system features."
        GROUP ipPermitGroup1
        DESCRIPTION   "The ipPermitGroup1 is an optional group
                      containing objects providing information about
                      the ip permit list feature."
        GROUP optionalSystemMiscGroup2
        DESCRIPTION   "The optionalSystemMiscGroup2 is an optional group
                      containing objects providing information about the
                      miscellaneous system features."
        GROUP filterGroup1
        DESCRIPTION   "The filterGroup is an optional group containing
                      objects providing information about the port
                      filtering feature."
        GROUP mcastGroup1
        DESCRIPTION   "The mcastGroup1 is an optional group containing
                      objects providing information about the
                      multicast features."
        GROUP portGroup1
        DESCRIPTION   "The portGroup1 is an optional group containing
                      objects providing information about the ports on
                      the device."
        GROUP chassisGroup1
        DESCRIPTION   "The chassisGroup1 is a group containing objects
                      providing information about the chassis of the
                      device. This group must be implemented by systems
                      that can have 3 or more power supplies."
        GROUP moduleGroup1
        DESCRIPTION    "The moduleGroup1 is an optional group containing
                       objects providing information about the modules
                       on the device."
        GROUP portCpbGroup2
        DESCRIPTION   "The portCpbGroup2 is an optional group containing
                      objects providing additional information about the
                      port capabilities on the device."
        ::= { ciscoStackMIBCompliances 2 }

ciscoStackgMIBCompliance3 MODULE-COMPLIANCE
        STATUS        deprecated
        DESCRIPTION   "The compliance statement for entities which
                      implement the Cisco stack MIB."
        MODULE        -- this module
        MANDATORY-GROUPS {
                systemMiscGroup,
                systemTrapGroup,
                chassisGroup,
                moduleGroup,
                portGroup
        }
        GROUP optionalSystemMiscGroup
        DESCRIPTION   "The OptionalSystemMiscGroup is an optional group
                      containing objects  providing information about
                      the miscellaneous system features."
        GROUP optionalSystemTrapGroup
        DESCRIPTION   "The OptionalSystemTrapGroup is an optional group
                      containing objects providing information about the
                      SNMP traps feature."
        GROUP optionalChassisGroup
        DESCRIPTION   "The OptionalChassisGroup is an optional group
                      containing objects providing information about the
                      chassis of the device."
        GROUP optionalModuleGroup
        DESCRIPTION   "The OptionalMooduleGroup is an optional group
                      containing objects providing information about the
                      modules on the device."
        GROUP optionalPortGroup
        DESCRIPTION   "The OptionalPortGroup is an optional group
                      containing objects providing information about the
                      ports on the device."
        GROUP systemTrafficGroup
        DESCRIPTION   "The systemTrafficGroup is an optional group
                      containing objects providing information about
                      the traffic meter feature."
        GROUP systemFddiGroup
        DESCRIPTION   "The systemFddiGroup is an optional group
                      containing objects providing information about
                      the FDDI ring feature."
        GROUP systemRmonGroup
        DESCRIPTION   "The systemRmonGroup is an optional group
                      containing objects providing information about the
                      extended RMON feature."
        GROUP authenticationGroup
        DESCRIPTION   "The authenticationGroup is an optional group
                      containing objects providing information about the
                      authentication features."
        GROUP tftpGroup
        DESCRIPTION   "The tftpGroup is an optional group containing
                      objects providing information about the tftp
                      upload/download features."
        GROUP brouteEnableGroup
        DESCRIPTION   "The brouteEnableGroup is an optional group
                      containing objects providing information about the
                      combined bridging/routing feature."
        GROUP filterGroup
        DESCRIPTION   "The filterGroup is an optional group containing
                       objects providing information about the port
                       filtering feature."
        GROUP monitorGroup
        DESCRIPTION   "The monitorGroup is an optional group containing
                      objects providing information about the port
                      monitoring feature, also known as the Switched
                      Port ANalyzer (SPAN) feature."
        GROUP vlanGroup
        DESCRIPTION   "The vlanGroup is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup
        DESCRIPTION   "The ipPermitGroup is an optional group containing
                      objects providing information about the ip permit
                      list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                      objects providing information about the tftp/rcp
                      or local file upload/download features."
        GROUP optionalSystemMiscGroup1
        DESCRIPTION   "The optionalSystemMiscGroup1 is an optional group
                      containing objects providing information about the
                      miscellaneous system features."
        GROUP ipPermitGroup1
        DESCRIPTION   "The ipPermitGroup1 is an optional group
                      containing objects providing information about
                      the ip permit list feature."
        GROUP optionalSystemMiscGroup2
        DESCRIPTION   "The optionalSystemMiscGroup2 is an optional group
                      containing objects providing information about the
                      miscellaneous system features."
        GROUP filterGroup1
        DESCRIPTION   "The filterGroup is an optional group containing
                      objects providing information about the port
                      filtering feature."
        GROUP mcastGroup1
        DESCRIPTION   "The mcastGroup1 is an optional group containing
                      objects providing information about the
                      multicast features."
        GROUP portGroup1
        DESCRIPTION   "The portGroup1 is an optional group containing
                      objects providing information about the ports on
                      the device."
        GROUP chassisGroup1
        DESCRIPTION   "The chassisGroup1 is a group containing objects
                      providing information about the chassis of the
                      device. This group must be implemented by systems
                      that can have 3 or more power supplies."
        GROUP moduleGroup1
        DESCRIPTION    "The moduleGroup1 is an optional group containing
                       objects providing information about the modules
                       on the device."
        GROUP portCpbGroup2
        DESCRIPTION   "The portCpbGroup2 is an optional group containing
                      objects providing additional information about the
                      port capabilities on the device."

        GROUP voiceGroup
        DESCRIPTION   "The voiceGroup is an optional group containing
                      objects providing information about the voice port
                      on the device."
        GROUP moduleGroup2
        DESCRIPTION    "The moduleGroup2 is an mandatory group
                       containing objects providing information about
                       the modules on the device."
        GROUP portCpbGroup3
        DESCRIPTION   "The portCpbGroup3 is an optional group containing
                      objects providing additional information about the
                      port capabilities on the device."
        GROUP vlanGroup1
        DESCRIPTION   "The vlanGroup1 is an optional group containing
                      objects providing information about the Virtual
                      LAN features."
        GROUP portGroup2
        DESCRIPTION   "The portGroup2 is an optional group containing
                      objects providing information about the ports on
                      the device."
        GROUP switchAccelerationModuleGroup
        DESCRIPTION   "This group is mandatory for implementations of
                      switch acceleration capability."
        GROUP optionalSystemMiscGroup3
        DESCRIPTION   "The optionalSystemMiscGroup3 is an optional group
                      containing objects providing information about the
                      miscellaneous system features."
        ::= { ciscoStackMIBCompliances 3 }

ciscoStackgMIBCompliance4 MODULE-COMPLIANCE
        STATUS        deprecated
        DESCRIPTION   "The compliance statement for entities which
                      implement the Cisco stack MIB."
        MODULE        -- this module
        MANDATORY-GROUPS {
                systemMiscGroup,
                systemTrapGroup,
                chassisGroup,
                moduleGroup,
                portGroup
        }
        GROUP optionalSystemMiscGroup
        DESCRIPTION   "The OptionalSystemMiscGroup is an optional group
                      containing objects  providing information about
                      the miscellaneous system features."
        GROUP optionalSystemTrapGroup
        DESCRIPTION   "The OptionalSystemTrapGroup is an optional group
                      containing objects providing information about the
                      SNMP traps feature."
        GROUP optionalChassisGroup
        DESCRIPTION   "The OptionalChassisGroup is an optional group
                      containing objects providing information about the
                      chassis of the device."
        GROUP optionalModuleGroup
        DESCRIPTION   "The OptionalMooduleGroup is an optional group
                      containing objects providing information about the
                      modules on the device."
        GROUP optionalPortGroup
        DESCRIPTION   "The OptionalPortGroup is an optional group
                      containing objects providing information about the
                      ports on the device."
        GROUP systemTrafficGroup
        DESCRIPTION   "The systemTrafficGroup is an optional group
                      containing objects providing information about the
                      traffic meter feature."
        GROUP systemFddiGroup
        DESCRIPTION   "The systemFddiGroup is an optional group
                      containing objects providing information about the
                      FDDI ring feature."
        GROUP systemRmonGroup
        DESCRIPTION   "The systemRmonGroup is an optional group
                      containing objects providing information about the
                      extended RMON feature."
        GROUP authenticationGroup
        DESCRIPTION   "The authenticationGroup is an optional group
                      containing objects providing information about the
                       authentication features."
        GROUP tftpGroup
        DESCRIPTION   "The tftpGroup is an optional group containing
                      objects providing information about the tftp
                      upload/download features."
        GROUP brouteEnableGroup
        DESCRIPTION   "The brouteEnableGroup is an optional group
                      containing objects providing information about the
                      combined bridging/routing feature."
        GROUP filterGroup
        DESCRIPTION   "The filterGroup is an optional group containing
                      objects providing information about the port
                      filtering feature."
        GROUP monitorGroup
        DESCRIPTION   "The monitorGroup is an optional group containing
                      objects providing information about the port
                      monitoring feature, also known as the Switched
                      Port ANalyzer (SPAN) feature."
        GROUP vlanGroup
        DESCRIPTION   "The vlanGroup is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects  providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup
        DESCRIPTION   "The ipPermitGroup is an optional group
                      containing objects providing information about
                      the ip permit list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                      objects providing information about the tftp/rcp
                      or local file upload/download features."
        GROUP optionalSystemMiscGroup1
        DESCRIPTION   "The optionalSystemMiscGroup1 is an optional group
                      containing objects providing information about the
                      miscellaneous system features."
        GROUP ipPermitGroup1
        DESCRIPTION   "The ipPermitGroup1 is an optional group
                      containing objects providing information about
                      the ip permit list feature."
        GROUP optionalSystemMiscGroup2
        DESCRIPTION   "The optionalSystemMiscGroup2 is an optional group
                      containing objects providing information about the
                      miscellaneous system features."
        GROUP filterGroup1
        DESCRIPTION   "The filterGroup is an optional group containing
                      objects providing information about the port
                      filtering feature."
        GROUP mcastGroup1
        DESCRIPTION   "The mcastGroup1 is an optional group containing
                      objects providing information about the
                      multicast features."
        GROUP portGroup1
        DESCRIPTION   "The portGroup1 is an optional group containing
                      objects providing information about the ports on
                      the device."
        GROUP chassisGroup1
        DESCRIPTION   "The chassisGroup1 is a group containing objects
                      providing information about the chassis of the
                      device. This group must be implemented by systems
                      that can have 3 or more power supplies."
        GROUP moduleGroup1
        DESCRIPTION   "The moduleGroup1 is an optional group containing
                      objects providing information about the modules
                       on the device."
        GROUP portCpbGroup2
        DESCRIPTION   "The portCpbGroup2 is an optional group containing
                      objects providing additional information about the
                      port capabilities on the device."

        GROUP voiceGroup
        DESCRIPTION   "The voiceGroup is an optional group containing
                      objects providing information about the voice port
                      on the device."
        GROUP moduleGroup2
        DESCRIPTION   "The moduleGroup2 is an mandatory group containing
                      objects providing information about the modules
                      on the device."
        GROUP portCpbGroup3
        DESCRIPTION   "The portCpbGroup3 is an optional group containing
                      objects providing additional information about the
                      port capabilities on the device."
        GROUP vlanGroup1
        DESCRIPTION   "The vlanGroup1 is an optional group containing
                      objects providing information about the Virtual
                      LAN features."
        GROUP portGroup2
        DESCRIPTION   "The portGroup2 is an optional group containing
                      objects providing information about the ports on
                      the device."
        GROUP switchAccelerationModuleGroup
        DESCRIPTION   "This group is mandatory for implementations of
                      switch acceleration capability."
        GROUP optionalSystemMiscGroup3
        DESCRIPTION   "The optionalSystemMiscGroup3 is an optional group
                      containing objects providing information about the
                      miscellaneous system features."
        GROUP optionalSystemMiscGroup4
        DESCRIPTION   "This group is an optional group containing
                      objects providing information about the
                      miscellaneous system features."
        GROUP vlanTrunkMappingGroup
        DESCRIPTION   "This group is mandatory for implementations of
                      trunk VLAN to VLAN association feature on the
                      device."
        GROUP portJumboFrameGroup
        DESCRIPTION   "This group is mandatory for implementations of
                      port jumbo frame feature on the device."
        GROUP portCpbGroup4
        DESCRIPTION   "The portCpbGroup4 is an optional group containing
                      objects providing additional information about the
                      port capabilities on the device."

        ::= { ciscoStackMIBCompliances 4 }

ciscoStackgMIBCompliance5 MODULE-COMPLIANCE
        STATUS        deprecated
        DESCRIPTION   "The compliance statement for entities which
                      implement the Cisco stack MIB."
        MODULE        -- this module
        MANDATORY-GROUPS {
                systemMiscGroup,
                systemTrapGroup,
                chassisGroup,
                moduleGroup,
                portGroup
        }
        GROUP optionalSystemMiscGroup
        DESCRIPTION   "The OptionalSystemMiscGroup is an optional group
                      containing objects  providing information about
                      the miscellaneous system features."
        GROUP optionalSystemTrapGroup
        DESCRIPTION   "The OptionalSystemTrapGroup is an optional group
                      containing objects providing information about the
                      SNMP traps feature."
        GROUP optionalChassisGroup
        DESCRIPTION   "The OptionalChassisGroup is an optional group
                      containing objects providing information about the
                      chassis of the device."
        GROUP optionalModuleGroup
        DESCRIPTION   "The OptionalMooduleGroup is an optional group
                      containing objects providing information about the
                      modules on the device."
        GROUP optionalPortGroup
        DESCRIPTION   "The OptionalPortGroup is an optional group
                      containing objects providing information about the
                      ports on the device."
        GROUP systemTrafficGroup
        DESCRIPTION   "The systemTrafficGroup is an optional group
                      containing objects providing information about the
                      traffic meter feature."
        GROUP systemFddiGroup
        DESCRIPTION   "The systemFddiGroup is an optional group
                      containing objects providing information about the
                      FDDI ring feature."
        GROUP systemRmonGroup
        DESCRIPTION   "The systemRmonGroup is an optional group
                      containing objects providing information about the
                      extended RMON feature."
        GROUP tftpGroup
        DESCRIPTION   "The tftpGroup is an optional group containing
                      objects providing information about the tftp
                      upload/download features."
        GROUP brouteEnableGroup
        DESCRIPTION   "The brouteEnableGroup is an optional group
                      containing objects providing information about the
                      combined bridging/routing feature."
        GROUP filterGroup
        DESCRIPTION   "The filterGroup is an optional group containing
                      objects providing information about the port
                      filtering feature."
        GROUP vlanGroup
        DESCRIPTION   "The vlanGroup is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects  providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup
        DESCRIPTION   "The ipPermitGroup is an optional group containing
                      objects providing information about the ip permit
                      list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                       objects providing information about the tftp/rcp
                       or local file upload/download features."
        GROUP optionalSystemMiscGroup1
        DESCRIPTION   "The optionalSystemMiscGroup1 is an optional group
                      containing objects providing information about the
                      miscellaneous system features."
        GROUP ipPermitGroup1
        DESCRIPTION   "The ipPermitGroup1 is an optional group
                      containing objects providing information about
                      the ip permit list feature."
        GROUP optionalSystemMiscGroup2
        DESCRIPTION   "The optionalSystemMiscGroup2 is an optional group
                      containing objects providing information about the
                      miscellaneous system features."
        GROUP filterGroup1
        DESCRIPTION   "The filterGroup is an optional group containing
                      objects providing information about the port
                      filtering feature."
        GROUP mcastGroup1
        DESCRIPTION   "The mcastGroup1 is an optional group containing
                      objects providing information about the
                      multicast features."
        GROUP portGroup1
        DESCRIPTION   "The portGroup1 is an optional group containing
                      objects providing information about the ports on
                      the device."
        GROUP chassisGroup1
        DESCRIPTION   "The chassisGroup1 is a group containing objects
                      providing information about the chassis of the
                      device. This group must be implemented by systems
                      that can have 3 or more power supplies."
        GROUP moduleGroup1
        DESCRIPTION    "The moduleGroup1 is an optional group containing
                       objects providing information about the modules
                       on the device."
        GROUP portCpbGroup2
        DESCRIPTION   "The portCpbGroup2 is an optional group containing
                      objects providing additional information about the
                      port capabilities on the device."

        GROUP voiceGroup
        DESCRIPTION   "The voiceGroup is an optional group containing
                      objects providing information about the voice port
                      on the device."
        GROUP moduleGroup2
        DESCRIPTION    "The moduleGroup2 is an mandatory group
                       containing objects providing information about
                       the modules on the device."
        GROUP portCpbGroup3
        DESCRIPTION   "The portCpbGroup3 is an optional group containing
                      objects providing additional information about the
                      port capabilities on the device."
        GROUP portGroup2
        DESCRIPTION   "The portGroup2 is an optional group containing
                      objects providing information about the ports on
                      the device."
        GROUP switchAccelerationModuleGroup
        DESCRIPTION   "This group is mandatory for implementations of
                      switch acceleration capability."
        GROUP optionalSystemMiscGroup3
        DESCRIPTION   "The optionalSystemMiscGroup3 is an optional group
                      containing objects providing information about the
                      miscellaneous system features."
        GROUP optionalSystemMiscGroup4
        DESCRIPTION   "This group is an optional group containing
                      objects providing information about the
                      miscellaneous system features."
        GROUP vlanTrunkMappingGroup
        DESCRIPTION   "This group is mandatory for implementations of
                      trunk VLAN to VLAN association feature on the
                      device."
        GROUP portJumboFrameGroup
        DESCRIPTION    "This group is mandatory for implementations of
                       port jumbo frame feature on the device."
        GROUP portCpbGroup4
        DESCRIPTION   "The portCpbGroup4 is an optional group containing
                      objects providing additional information about the
                      port capabilities on the device."
        GROUP fileCopyGroup2
        DESCRIPTION   "The fileCopyGroup2 is an optional group
                      containing objects providing additional
                      information about tftp/rcp or local file
                      upload/download features."
        GROUP systemRmonGroup2
        DESCRIPTION   "The systemRmonGroup2 is an optional group
                      containing objects providing information about
                      RMON max memory usage control."
        GROUP filterGroup2
        DESCRIPTION   "The filterGroup2 is an optional group containing
                      objects providing information about the
                      unicast/multicast port filtering feature."
        GROUP optionalSystemMiscGroup5
        DESCRIPTION   "The optionalSystemMiscGroup5 is an optional group
                      containing objects providing information about
                      miscellaneous system features."
        GROUP syslogGroup2
        DESCRIPTION   "The syslogGroup2 is an optional group containing
                      objects providing information about whether the
                      syslog messages should be sent to telnet
                      sessions."
        GROUP systemStatusGroup
        DESCRIPTION   "The systemStatusGroup is an optional group
                      containing objects providing information about
                      system LED status."
        GROUP configurationGroup
        DESCRIPTION   "The configurationGroup is an optional group
                      containing objects providing information about
                      the configuration mode to store the configuration
                      information."
        GROUP filterGroup3
        DESCRIPTION   "The filterGroup3 is an optional group containing
                      objects providing information about Broadcast
                      Suppression Violation for port filtering
                      feature."
        GROUP portGroup3
        DESCRIPTION   "The portGroup3 is an optional group containing
                      objects providing information about additional
                      information about the ports on the device."
        GROUP portCpbGroup5
        DESCRIPTION   "The portCpbGroup5 is an optional group containing
                      objects providing additional information about
                      the port capabilities on the device."
        GROUP authenticationGroup1
        DESCRIPTION   "The authenticationGroup1 is an optional group
                      containing objects providing information about the
                      authentication features."

        ::= { ciscoStackMIBCompliances 5 }

ciscoStackgMIBCompliance6 MODULE-COMPLIANCE
        STATUS        deprecated
        DESCRIPTION   "The compliance statement for entities which
                      implement the Cisco stack MIB."
        MODULE        -- this module
        MANDATORY-GROUPS {
                systemMiscGroup1,
                systemTrapGroup1,
                chassisGroup,
                moduleGroup,
                portGroup4
        }
        GROUP optionalSystemMiscGroup
        DESCRIPTION   "The OptionalSystemMiscGroup is an optional group
                      containing objects  providing information about
                      the miscellaneous system features."
        GROUP optionalSystemTrapGroup
        DESCRIPTION   "The OptionalSystemTrapGroup is an optional group
                      containing objects providing information about the
                      SNMP traps feature."
        GROUP optionalChassisGroup1
        DESCRIPTION   "The OptionalChassisGroup1 is an optional group
                      containing objects providing information about the
                      chassis of the device."
        GROUP optionalModuleGroup
        DESCRIPTION   "The OptionalMooduleGroup is an optional group
                      containing objects providing information about the
                      modules on the device."
        GROUP optionalPortGroup1
        DESCRIPTION   "The OptionalPortGroup1 is an optional group
                      containing objects providing information about the
                      ports on the device."
        GROUP systemTrafficGroup
        DESCRIPTION   "The systemTrafficGroup is an optional group
                      containing objects providing information about the
                      traffic meter feature."
        GROUP systemFddiGroup
        DESCRIPTION   "The systemFddiGroup is an optional group
                      containing objects providing information about the
                      FDDI ring feature."
        GROUP systemRmonGroup
        DESCRIPTION   "The systemRmonGroup is an optional group
                      containing objects providing information about the
                      extended RMON feature."
        GROUP tftpGroup
        DESCRIPTION   "The tftpGroup is an optional group containing
                      objects providing information about the tftp
                      upload/download features."
        GROUP brouteEnableGroup
        DESCRIPTION   "The brouteEnableGroup is an optional group
                      containing objects providing information about the
                      combined bridging/routing feature."
        GROUP filterGroup
        DESCRIPTION   "The filterGroup is an optional group containing
                      objects providing information about the port
                      filtering feature."
        GROUP vlanGroup2
        DESCRIPTION   "The vlanGroup2 is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects  providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup2
        DESCRIPTION   "The ipPermitGroup2 is an optional group
                      containing objects providing information
                      about the ip permit list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                       objects providing information about the tftp/rcp
                       or local file upload/download features."
        GROUP optionalSystemMiscGroup1
        DESCRIPTION   "The optionalSystemMiscGroup1 is an optional group
                      containing objects providing information about the
                      miscellaneous system features."
        GROUP ipPermitGroup1
        DESCRIPTION   "The ipPermitGroup1 is an optional group
                      containing objects providing information about
                      the ip permit list feature."
        GROUP optionalSystemMiscGroup6
        DESCRIPTION   "The optionalSystemMiscGroup6 is an optional group
                      containing objects providing information about the
                      miscellaneous system features."
        GROUP filterGroup1
        DESCRIPTION   "The filterGroup1 is an optional group containing
                      objects providing information about the port
                      filtering feature."
        GROUP mcastGroup1
        DESCRIPTION   "The mcastGroup1 is an optional group containing
                      objects providing information about the
                      multicast features."
        GROUP portGroup1
        DESCRIPTION   "The portGroup1 is an optional group containing
                      objects providing information about the ports on
                      the device."
        GROUP chassisGroup1
        DESCRIPTION   "The chassisGroup1 is a group containing objects
                      providing information about the chassis of the
                      device. This group must be implemented by systems
                      that can have 3 or more power supplies."
        GROUP moduleGroup1
        DESCRIPTION    "The moduleGroup1 is an optional group containing
                       objects providing information about the modules
                       on the device."
        GROUP portCpbGroup2
        DESCRIPTION   "The portCpbGroup2 is an optional group containing
                      objects providing additional information about the
                      port capabilities on the device."

        GROUP voiceGroup
        DESCRIPTION   "The voiceGroup is an optional group containing
                      objects providing information about the voice port
                      on the device."
        GROUP moduleGroup2
        DESCRIPTION    "The moduleGroup2 is an mandatory group
                       containing objects providing information about
                       the modules on the device."
        GROUP portCpbGroup3
        DESCRIPTION   "The portCpbGroup3 is an optional group containing
                      objects providing additional information about the
                      port capabilities on the device."
        GROUP portGroup2
        DESCRIPTION   "The portGroup2 is an optional group containing
                      objects providing information about the ports on
                      the device."
        GROUP switchAccelerationModuleGroup
        DESCRIPTION   "This group is mandatory for implementations of
                      switch acceleration capability."
        GROUP optionalSystemMiscGroup3
        DESCRIPTION   "The optionalSystemMiscGroup3 is an optional group
                      containing objects providing information about the
                      miscellaneous system features."
        GROUP optionalSystemMiscGroup4
        DESCRIPTION   "This group is an optional group containing
                      objects providing information about the
                      miscellaneous system features."
        GROUP vlanTrunkMappingGroup
        DESCRIPTION   "This group is mandatory for implementations of
                      trunk VLAN to VLAN association feature on the
                      device."
        GROUP portJumboFrameGroup
        DESCRIPTION    "This group is mandatory for implementations of
                       port jumbo frame feature on the device."
        GROUP portCpbGroup4
        DESCRIPTION   "The portCpbGroup4 is an optional group containing
                      objects providing additional information about the
                      port capabilities on the device."
        GROUP fileCopyGroup2
        DESCRIPTION   "The fileCopyGroup2 is an optional group
                      containing objects providing additional
                      information about tftp/rcp or local file
                      upload/download features."
        GROUP systemRmonGroup2
        DESCRIPTION   "The systemRmonGroup2 is an optional group
                      containing objects providing information about
                      RMON max memory usage control."
        GROUP filterGroup2
        DESCRIPTION   "The filterGroup2 is an optional group containing
                      objects providing information about the
                      unicast/multicast port filtering feature."
        GROUP optionalSystemMiscGroup5
        DESCRIPTION   "The optionalSystemMiscGroup5 is an optional group
                      containing objects providing information about
                      miscellaneous system features."
        GROUP syslogGroup2
        DESCRIPTION   "The syslogGroup2 is an optional group containing
                      objects providing information about whether the
                      syslog messages should be sent to telnet
                      sessions."
        GROUP systemStatusGroup
        DESCRIPTION   "The systemStatusGroup is an optional group
                      containing objects providing information about
                      system LED status."
        GROUP configurationGroup
        DESCRIPTION   "The configurationGroup is an optional group
                      containing objects providing information about
                      the configuration mode to store the configuration
                      information."
        GROUP filterGroup3
        DESCRIPTION   "The filterGroup3 is an optional group containing
                      objects providing information about Broadcast
                      Suppression Violation for port filtering
                      feature."
        GROUP portGroup3
        DESCRIPTION   "The portGroup3 is an optional group containing
                      objects providing information about additional
                      information about the ports on the device."
        GROUP portCpbGroup5
        DESCRIPTION   "The portCpbGroup5 is an optional group containing
                      objects providing additional information about
                      the port capabilities on the device."
        GROUP authenticationGroup1
        DESCRIPTION   "The authenticationGroup1 is an optional group
                      containing objects providing information about the
                      authentication features."

        ::= { ciscoStackMIBCompliances 6 }

ciscoStackgMIBCompliance7 MODULE-COMPLIANCE
        STATUS        deprecated
        DESCRIPTION   "The compliance statement for entities which
                      implement the Cisco stack MIB."
        MODULE        -- this module
        MANDATORY-GROUPS {
                systemMiscGroup1,
                systemTrapGroup2,
                chassisGroup,
                moduleGroup,
                portGroup4
        }
        GROUP optionalSystemMiscGroup
        DESCRIPTION   "The OptionalSystemMiscGroup is an optional group
                      containing objects  providing information about
                      the miscellaneous system features."
        GROUP optionalChassisGroup1
        DESCRIPTION   "The OptionalChassisGroup1 is an optional group
                      containing objects providing information about the
                      chassis of the device."
        GROUP optionalModuleGroup
        DESCRIPTION   "The OptionalMooduleGroup is an optional group
                      containing objects providing information about the
                      modules on the device."
        GROUP optionalPortGroup1
        DESCRIPTION   "The OptionalPortGroup1 is an optional group
                      containing objects providing information about the
                      ports on the device."
        GROUP systemTrafficGroup
        DESCRIPTION   "The systemTrafficGroup is an optional group
                      containing objects providing information about the
                      traffic meter feature."
        GROUP systemFddiGroup
        DESCRIPTION   "The systemFddiGroup is an optional group
                      containing objects providing information about the
                      FDDI ring feature."
        GROUP systemRmonGroup
        DESCRIPTION   "The systemRmonGroup is an optional group
                      containing objects providing information about the
                      extended RMON feature."
        GROUP tftpGroup
        DESCRIPTION   "The tftpGroup is an optional group containing
                      objects providing information about the tftp
                      upload/download features."
        GROUP brouteEnableGroup
        DESCRIPTION   "The brouteEnableGroup is an optional group
                      containing objects providing information about the
                      combined bridging/routing feature."
        GROUP filterGroup
        DESCRIPTION   "The filterGroup is an optional group containing
                      objects providing information about the port
                      filtering feature."
        GROUP vlanGroup2
        DESCRIPTION   "The vlanGroup2 is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects  providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup2
        DESCRIPTION   "The ipPermitGroup2 is an optional group
                      containing objects providing information
                      about the ip permit list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                       objects providing information about the tftp/rcp
                       or local file upload/download features."
        GROUP optionalSystemMiscGroup1
        DESCRIPTION   "The optionalSystemMiscGroup1 is an optional group
                      containing objects providing information about the
                      miscellaneous system features."
        GROUP ipPermitGroup1
        DESCRIPTION   "The ipPermitGroup1 is an optional group
                      containing objects providing information about
                      the ip permit list feature."
        GROUP optionalSystemMiscGroup6
        DESCRIPTION   "The optionalSystemMiscGroup6 is an optional group
                      containing objects providing information about the
                      miscellaneous system features."
        GROUP filterGroup1
        DESCRIPTION   "The filterGroup1 is an optional group containing
                      objects providing information about the port
                      filtering feature."
        GROUP mcastGroup1
        DESCRIPTION   "The mcastGroup1 is an optional group containing
                      objects providing information about the
                      multicast features."
        GROUP portGroup1
        DESCRIPTION   "The portGroup1 is an optional group containing
                      objects providing information about the ports on
                      the device."
        GROUP chassisGroup1
        DESCRIPTION   "The chassisGroup1 is a group containing objects
                      providing information about the chassis of the
                      device. This group must be implemented by systems
                      that can have 3 or more power supplies."
        GROUP moduleGroup1
        DESCRIPTION    "The moduleGroup1 is an optional group containing
                       objects providing information about the modules
                       on the device."
        GROUP portCpbGroup2
        DESCRIPTION   "The portCpbGroup2 is an optional group containing
                      objects providing additional information about the
                      port capabilities on the device."

        GROUP voiceGroup
        DESCRIPTION   "The voiceGroup is an optional group containing
                      objects providing information about the voice port
                      on the device."
        GROUP moduleGroup2
        DESCRIPTION    "The moduleGroup2 is an mandatory group
                       containing objects providing information about
                       the modules on the device."
        GROUP portCpbGroup3
        DESCRIPTION   "The portCpbGroup3 is an optional group containing
                      objects providing additional information about the
                      port capabilities on the device."
        GROUP portGroup2
        DESCRIPTION   "The portGroup2 is an optional group containing
                      objects providing information about the ports on
                      the device."
        GROUP switchAccelerationModuleGroup
        DESCRIPTION   "This group is mandatory for implementations of
                      switch acceleration capability."
        GROUP optionalSystemMiscGroup3
        DESCRIPTION   "The optionalSystemMiscGroup3 is an optional group
                      containing objects providing information about the
                      miscellaneous system features."
        GROUP optionalSystemMiscGroup4
        DESCRIPTION   "This group is an optional group containing
                      objects providing information about the
                      miscellaneous system features."
        GROUP vlanTrunkMappingGroup
        DESCRIPTION   "This group is mandatory for implementations of
                      trunk VLAN to VLAN association feature on the
                      device."
        GROUP portJumboFrameGroup
        DESCRIPTION    "This group is mandatory for implementations of
                       port jumbo frame feature on the device."
        GROUP portCpbGroup4
        DESCRIPTION   "The portCpbGroup4 is an optional group containing
                      objects providing additional information about the
                      port capabilities on the device."
        GROUP fileCopyGroup2
        DESCRIPTION   "The fileCopyGroup2 is an optional group
                      containing objects providing additional
                      information about tftp/rcp or local file
                      upload/download features."
        GROUP systemRmonGroup2
        DESCRIPTION   "The systemRmonGroup2 is an optional group
                      containing objects providing information about
                      RMON max memory usage control."
        GROUP filterGroup2
        DESCRIPTION   "The filterGroup2 is an optional group containing
                      objects providing information about the
                      unicast/multicast port filtering feature."
        GROUP optionalSystemMiscGroup5
        DESCRIPTION   "The optionalSystemMiscGroup5 is an optional group
                      containing objects providing information about
                      miscellaneous system features."
        GROUP syslogGroup2
        DESCRIPTION   "The syslogGroup2 is an optional group containing
                      objects providing information about whether the
                      syslog messages should be sent to telnet
                      sessions."
        GROUP systemStatusGroup
        DESCRIPTION   "The systemStatusGroup is an optional group
                      containing objects providing information about
                      system LED status."
        GROUP configurationGroup
        DESCRIPTION   "The configurationGroup is an optional group
                      containing objects providing information about
                      the configuration mode to store the configuration
                      information."
        GROUP filterGroup3
        DESCRIPTION   "The filterGroup3 is an optional group containing
                      objects providing information about Broadcast
                      Suppression Violation for port filtering
                      feature."
        GROUP portGroup3
        DESCRIPTION   "The portGroup3 is an optional group containing
                      objects providing information about additional
                      information about the ports on the device."
        GROUP portCpbGroup5
        DESCRIPTION   "The portCpbGroup5 is an optional group containing
                      objects providing additional information about
                      the port capabilities on the device."
        GROUP optionalSystemTrapGroup1
        DESCRIPTION   "The OptionalSystemTrapGroup1 is an optional group
                      containing objects providing information about the
                      SNMP traps feature."
        GROUP authenticationGroup2
        DESCRIPTION   "The authenticationGroup2 is an optional group
                      containing objects providing information about the
                      authentication features."

        GROUP notificationGroup
        DESCRIPTION   "The notificationGroup is an optional group
                      containing notifications supported on the device."

        ::= { ciscoStackMIBCompliances 7 }

ciscoStackgMIBCompliance8 MODULE-COMPLIANCE
        STATUS        current
        DESCRIPTION   "The compliance statement for entities which
                      implement the Cisco stack MIB."
        MODULE        -- this module
        MANDATORY-GROUPS {
                systemMiscGroup1,
                systemTrapGroup2,
                chassisGroup,
                moduleGroup,
                portGroup4
        }
        GROUP optionalSystemMiscGroup
        DESCRIPTION   "The OptionalSystemMiscGroup is an optional group
                      containing objects  providing information about
                      the miscellaneous system features."
        GROUP optionalChassisGroup1
        DESCRIPTION   "The OptionalChassisGroup1 is an optional group
                      containing objects providing information about the
                      chassis of the device."
        GROUP optionalModuleGroup
        DESCRIPTION   "The OptionalMooduleGroup is an optional group
                      containing objects providing information about the
                      modules on the device."
        GROUP optionalPortGroup1
        DESCRIPTION   "The OptionalPortGroup1 is an optional group
                      containing objects providing information about the
                      ports on the device."
        GROUP systemTrafficGroup
        DESCRIPTION   "The systemTrafficGroup is an optional group
                      containing objects providing information about the
                      traffic meter feature."
        GROUP systemFddiGroup
        DESCRIPTION   "The systemFddiGroup is an optional group
                      containing objects providing information about the
                      FDDI ring feature."
        GROUP systemRmonGroup
        DESCRIPTION   "The systemRmonGroup is an optional group
                      containing objects providing information about the
                      extended RMON feature."
        GROUP tftpGroup
        DESCRIPTION   "The tftpGroup is an optional group containing
                      objects providing information about the tftp
                      upload/download features."
        GROUP brouteEnableGroup
        DESCRIPTION   "The brouteEnableGroup is an optional group
                      containing objects providing information about the
                      combined bridging/routing feature."
        GROUP filterGroup
        DESCRIPTION   "The filterGroup is an optional group containing
                      objects providing information about the port
                      filtering feature."
        GROUP vlanGroup2
        DESCRIPTION   "The vlanGroup2 is an optional group containing
                      objects providing information about the Virtual
                      LAN features."
        GROUP vmpsGroup
        DESCRIPTION   "The vmps is an optional group containing objects
                      providing information about the Vlan Membership
                      Policy Server feature."
        GROUP tokenRingGroup
        DESCRIPTION   "The tokenRingGroup is an optional group
                      containing objects  providing information about
                      the tokenring features."
        GROUP mcastGroup
        DESCRIPTION   "The mcastGroup is an optional group containing
                      objects providing information about the multicast
                      features."
        GROUP dnsGroup
        DESCRIPTION   "The dnsGroup is an optional group containing
                      objects providing information about the DNS
                      feature."
        GROUP syslogGroup
        DESCRIPTION   "The syslogGroup is an optional group containing
                      objects providing information about the system log
                      feature."
        GROUP ntpGroup
        DESCRIPTION   "The ntpGroup is an optional group containing
                      objects providing information about the network
                      time protocol feature."
        GROUP ipPermitGroup2
        DESCRIPTION   "The ipPermitGroup2 is an optional group
                      containing objects providing information
                      about the ip permit list feature."
        GROUP mdgGatewayGroup
        DESCRIPTION   "The mdgGatewayGroup is an optional group
                      containing objects  providing information about
                      the multiple default gateway feature."
        GROUP traceRouteGroup
        DESCRIPTION   "The traceRouteGroup is an optional group
                      containing objects  providing information about
                      the trace route feature."
        GROUP ntpAuthenticationGroup
        DESCRIPTION   "The ntpAuthenticationGroup is an optional group
                      containing objects providing information about the
                      network time protocol authentication feature."
        GROUP tokenRingSoftErrorMonitorGroup
        DESCRIPTION   "The tokenRingSoftErrorMonitorGroup is an optional
                      group containing objects providing information
                      about the token ring port soft error monitoring
                      feature."
        GROUP portCpbGroup1
        DESCRIPTION   "The portCpbGroup1 is an optional group containing
                      objects providing additional information about the
                      port capabilities on the device."
        GROUP portSecurityGroup1
        DESCRIPTION   "The portSecurityGroup1 is an optional group
                      containing objects providing additional
                      information for supporting port security feature
                      with the multiple secured source MAC addresses."
        GROUP fileCopyGroup
        DESCRIPTION   "The fileCopyGroup is an optional group containing
                       objects providing information about the tftp/rcp
                       or local file upload/download features."
        GROUP optionalSystemMiscGroup1
        DESCRIPTION   "The optionalSystemMiscGroup1 is an optional group
                      containing objects providing information about the
                      miscellaneous system features."
        GROUP ipPermitGroup1
        DESCRIPTION   "The ipPermitGroup1 is an optional group
                      containing objects providing information about
                      the ip permit list feature."
        GROUP optionalSystemMiscGroup6
        DESCRIPTION   "The optionalSystemMiscGroup6 is an optional group
                      containing objects providing information about the
                      miscellaneous system features."
        GROUP filterGroup1
        DESCRIPTION   "The filterGroup1 is an optional group containing
                      objects providing information about the port
                      filtering feature."
        GROUP mcastGroup1
        DESCRIPTION   "The mcastGroup1 is an optional group containing
                      objects providing information about the
                      multicast features."
        GROUP portGroup1
        DESCRIPTION   "The portGroup1 is an optional group containing
                      objects providing information about the ports on
                      the device."
        GROUP chassisGroup1
        DESCRIPTION   "The chassisGroup1 is a group containing objects
                      providing information about the chassis of the
                      device. This group must be implemented by systems
                      that can have 3 or more power supplies."
        GROUP moduleGroup1
        DESCRIPTION    "The moduleGroup1 is an optional group containing
                       objects providing information about the modules
                       on the device."
        GROUP portCpbGroup2
        DESCRIPTION   "The portCpbGroup2 is an optional group containing
                      objects providing additional information about the
                      port capabilities on the device."

        GROUP voiceGroup
        DESCRIPTION   "The voiceGroup is an optional group containing
                      objects providing information about the voice port
                      on the device."
        GROUP moduleGroup2
        DESCRIPTION    "The moduleGroup2 is an mandatory group
                       containing objects providing information about
                       the modules on the device."
        GROUP portCpbGroup3
        DESCRIPTION   "The portCpbGroup3 is an optional group containing
                      objects providing additional information about the
                      port capabilities on the device."
        GROUP portGroup2
        DESCRIPTION   "The portGroup2 is an optional group containing
                      objects providing information about the ports on
                      the device."
        GROUP switchAccelerationModuleGroup
        DESCRIPTION   "This group is mandatory for implementations of
                      switch acceleration capability."
        GROUP optionalSystemMiscGroup3
        DESCRIPTION   "The optionalSystemMiscGroup3 is an optional group
                      containing objects providing information about the
                      miscellaneous system features."
        GROUP optionalSystemMiscGroup4
        DESCRIPTION   "This group is an optional group containing
                      objects providing information about the
                      miscellaneous system features."
        GROUP vlanTrunkMappingGroup
        DESCRIPTION   "This group is mandatory for implementations of
                      trunk VLAN to VLAN association feature on the
                      device."
        GROUP portJumboFrameGroup
        DESCRIPTION    "This group is mandatory for implementations of
                       port jumbo frame feature on the device."
        GROUP portCpbGroup4
        DESCRIPTION   "The portCpbGroup4 is an optional group containing
                      objects providing additional information about the
                      port capabilities on the device."
        GROUP fileCopyGroup2
        DESCRIPTION   "The fileCopyGroup2 is an optional group
                      containing objects providing additional
                      information about tftp/rcp or local file
                      upload/download features."
        GROUP systemRmonGroup2
        DESCRIPTION   "The systemRmonGroup2 is an optional group
                      containing objects providing information about
                      RMON max memory usage control."
        GROUP filterGroup2
        DESCRIPTION   "The filterGroup2 is an optional group containing
                      objects providing information about the
                      unicast/multicast port filtering feature."
        GROUP optionalSystemMiscGroup5
        DESCRIPTION   "The optionalSystemMiscGroup5 is an optional group
                      containing objects providing information about
                      miscellaneous system features."
        GROUP syslogGroup2
        DESCRIPTION   "The syslogGroup2 is an optional group containing
                      objects providing information about whether the
                      syslog messages should be sent to telnet
                      sessions."
        GROUP systemStatusGroup
        DESCRIPTION   "The systemStatusGroup is an optional group
                      containing objects providing information about
                      system LED status."
        GROUP configurationGroup
        DESCRIPTION   "The configurationGroup is an optional group
                      containing objects providing information about
                      the configuration mode to store the configuration
                      information."
        GROUP filterGroup3
        DESCRIPTION   "The filterGroup3 is an optional group containing
                      objects providing information about Broadcast
                      Suppression Violation for port filtering
                      feature."
        GROUP portGroup3
        DESCRIPTION   "The portGroup3 is an optional group containing
                      objects providing information about additional
                      information about the ports on the device."
        GROUP portCpbGroup5
        DESCRIPTION   "The portCpbGroup5 is an optional group containing
                      objects providing additional information about
                      the port capabilities on the device."
        GROUP optionalSystemTrapGroup1
        DESCRIPTION   "The OptionalSystemTrapGroup1 is an optional group
                      containing objects providing information about the
                      SNMP traps feature."
        GROUP authenticationGroup2
        DESCRIPTION   "The authenticationGroup2 is an optional group
                      containing objects providing information about the
                      authentication features."
        GROUP notificationGroup
        DESCRIPTION   "The notificationGroup is an optional group
                      containing notifications supported on the device."
        GROUP ipPermitGroup3
        DESCRIPTION   "The ipPermitGroup3 is an optional group containing 
                      objects providing information about the ip permit 
                      connection limit for a specific host."
        
        ::= { ciscoStackMIBCompliances 8 }

-- units of conformance

systemMiscGroup OBJECT-GROUP
        OBJECTS {
                sysMgmtType,
                sysIpAddr,              -- deprecated
                sysNetMask,             -- deprecated
                sysBroadcast,           -- deprecated
                sysAttachType,
                sysReset,               -- deprecated
                sysBaudRate,
                sysInsertMode,
                sysClearMacTime,        -- deprecated
                sysClearPortTime,       -- deprecated
                sysEnableModem,
                sysEnableRedirects,
                sysArpAgingTime,
                sysCommunityRwa,
                sysCommunityRw,
                sysCommunityRo,
                sysIpVlan
        }
        STATUS        deprecated
        DESCRIPTION   "A collection of objects providing information
                      about the miscellaneous system features."
        ::= { ciscoStackMIBGroups 1 }
systemTrapGroup OBJECT-GROUP
        OBJECTS {
                sysTrapReceiverAddr,    -- deprecated
                sysTrapReceiverType,    -- deprecated
                sysTrapReceiverComm,    -- deprecated
                sysEnableChassisTraps,
                sysEnableModuleTraps,
                sysEnableBridgeTraps,
                sysEnableRepeaterTraps
        }
        STATUS        deprecated
        DESCRIPTION   "A collection of objects providing information
                      about the SNMP traps feature."
        ::= { ciscoStackMIBGroups 2 }
chassisGroup OBJECT-GROUP
        OBJECTS {
                chassisSysType,
                chassisBkplType,
                chassisPs1Type,
                chassisPs1Status,
                chassisPs1TestResult,
                chassisPs2Type,
                chassisPs2Status,
                chassisPs2TestResult,
                chassisFanStatus,
                chassisFanTestResult,
                chassisMinorAlarm,
                chassisMajorAlarm,
                chassisTempAlarm,
                chassisNumSlots
        }
        STATUS        current
        DESCRIPTION   "A collection of objects providing information
                      about the chassis of the device.

                      Implementation of this group is mandatory."
        ::= { ciscoStackMIBGroups 3 }

moduleGroup OBJECT-GROUP
        OBJECTS {
                moduleIndex,
                moduleType,
                moduleStatus,
                moduleTestResult,
                moduleAction,
                moduleName,
                moduleNumPorts,
                modulePortStatus,
                moduleSubType,
                moduleSerialNumberString
                    }
        STATUS        current
        DESCRIPTION   "A collection of objects providing information
                      about the modules on the device.

                      Implementation of this group is mandatory."
        ::= { ciscoStackMIBGroups 4 }
portGroup OBJECT-GROUP
        OBJECTS {
                portModuleIndex,
                portIndex,
                portCrossIndex,
                portName,
                portType,
                portOperStatus,
                portCrossGroupIndex,
                portAdditionalStatus,
                portAdminSpeed,
                portDuplex,
                portIfIndex,
                portSpantreeFastStart,                -- deprecated
                portAdminRxFlowControl,
                portOperRxFlowControl,
                portAdminTxFlowControl,
                portOperTxFlowControl,
                portMacControlTransmitFrames,
                portMacControlReceiveFrames,
                portMacControlPauseTransmitFrames,
                portMacControlPauseReceiveFrames,
                portMacControlUnknownProtocolFrames,
                portLinkFaultStatus
        }
        STATUS        deprecated
        DESCRIPTION   "A collection of objects providing information
                      about the ports on the device."
        ::= { ciscoStackMIBGroups 5 }
optionalSystemMiscGroup OBJECT-GROUP
        OBJECTS {
                sysConfigChangeTime,
                sysBannerMotd,
                sysConfigChangeInfo,
                sysConfigRegister,
                sysBootVariable,
                sysBootedImage
        }
        STATUS        current
        DESCRIPTION   "A collection of objects providing information
                      about the miscellaneous system features.

                      Implementation of this group is optional."
        ::= { ciscoStackMIBGroups 6 }
optionalSystemTrapGroup OBJECT-GROUP
        OBJECTS {
                sysEnableIpPermitTraps,
                sysEnableVmpsTraps,
                sysEnableConfigTraps,
                sysEnableEntityTrap,
                sysEnableStpxTrap
        }
        STATUS        deprecated
        DESCRIPTION   "A collection of objects providing information
                      about the SNMP traps feature.

                      Implementation of this group is optional."
        ::= { ciscoStackMIBGroups 7 }

optionalChassisGroup OBJECT-GROUP
        OBJECTS {
                chassisPs1TestResult,
                chassisPs2TestResult,
                chassisFanTestResult,
                chassisSlotConfig,
                chassisModel,
                chassisComponentIndex,        -- deprecated
                chassisComponentType,         -- deprecated
                chassisComponentSerialNumber, -- deprecated
                chassisComponentHwVersion,    -- deprecated
                chassisComponentModel,        -- deprecated
                chassisSerialNumberString     -- deprecated
        }
        STATUS        deprecated
        DESCRIPTION   "A collection of objects providing information
                      about the chassis of the device."
        ::= { ciscoStackMIBGroups 8 }
optionalModuleGroup OBJECT-GROUP
        OBJECTS {
                moduleTestResult,
                moduleModel,
                moduleHwVersion,
                moduleFwVersion,
                moduleSwVersion,
                moduleStandbyStatus,
                moduleIPAddress,
                moduleIPAddressVlan,
                moduleSubType2,
                moduleSlotNum
                    }
        STATUS        current
        DESCRIPTION   "A collection of objects providing information
                      about the modules on the device.

                      Implementation of this group is Optional."
        ::= { ciscoStackMIBGroups 9 }
optionalPortGroup OBJECT-GROUP
        OBJECTS {
                portSecurityModuleIndex,
                portSecurityPortIndex,
                portSecurityAdminStatus,
                portSecurityOperStatus,
                portSecurityLastSrcAddr,
                portSecuritySecureSrcAddr,
                portChannelModuleIndex,           -- deprecated
                portChannelPortIndex,             -- deprecated
                portChannelPorts,                 -- deprecated
                portChannelAdminStatus,           -- deprecated
                portChannelOperStatus,            -- deprecated
                portChannelNeighbourDeviceId,     -- deprecated
                portChannelNeighbourPortId,       -- deprecated
                portChannelProtInPackets,         -- deprecated
                portChannelProtOutPackets,        -- deprecated
                portChannelIfIndex,               -- deprecated
                portCpbModuleIndex,
                portCpbPortIndex,
                portCpbSpeed,
                portCpbDuplex,
                portCpbTrunkEncapsulationType,
                portCpbTrunkMode,
                portCpbChannel,
                portCpbBroadcastSuppression,
                portCpbFlowControl,
                portCpbSecurity,
                portCpbVlanMembership,
                portCpbPortfast,
                portTopNControlIndex,
                portTopNRateBase,
                portTopNType,
                portTopNMode,
                portTopNReportStatus,
                portTopNDuration,
                portTopNTimeRemaining,
                portTopNStartTime,
                portTopNRequestedSize,
                portTopNGrantedSize,
                portTopNOwner,
                portTopNStatus,
                portTopNIndex,
                portTopNModuleNumber,
                portTopNPortNumber,
                portTopNUtilization,
                portTopNIOOctets,
                portTopNIOPkts,
                portTopNIOBroadcast,
                portTopNIOMulticast,
                portTopNInErrors,
                portTopNBufferOverFlow
        }
        STATUS        deprecated
        DESCRIPTION   "A collection of objects providing information
                      about the ports on the device.

                      Implementation of this group is Optional."
        ::= { ciscoStackMIBGroups 10 }
systemTrafficGroup OBJECT-GROUP
        OBJECTS {
                sysTrafficMeterType,
                sysTraffic,
                sysTrafficPeak,
                sysTrafficPeakTime,
                sysTrafficMeter,
                sysTrafficMeterPeak,
                sysTrafficMeterPeakTime
        }
        STATUS        current
        DESCRIPTION   "A collection of objects providing information
                      about the traffic meter feature.

                      Implementation of this group is optional. If the
                      traffic meter feature is supported, the entire
                      group should be implemented."
        ::= { ciscoStackMIBGroups 11 }
systemFddiGroup OBJECT-GROUP
        OBJECTS {
                sysFddiRingSMTIndex,
                sysFddiRingAddress,
                sysFddiRingNext

        }
        STATUS        current
        DESCRIPTION   "A collection of objects providing information
                      about the FDDI ring feature.

                      Implementation of this group is optional. If the
                      FDDI ring feature is supported, the entire group
                      should be implemented."
        ::= { ciscoStackMIBGroups 12 }
systemRmonGroup OBJECT-GROUP
        OBJECTS {
                sysEnableRmon,
                sysExtendedRmonVlanModeEnable,
                sysExtendedRmonNetflowPassword,
                sysExtendedRmonNetflowEnable,
                sysExtendedRmonVlanAgentEnable,
                sysExtendedRmonEnable
        }
        STATUS        current
        DESCRIPTION   "A collection of objects providing information
                      about the extended RMON feature.

                      Implementation of this group is optional. If the
                      extended RMON feature is supported, the entire
                      group should be implemented."
        ::= { ciscoStackMIBGroups 13 }
authenticationGroup OBJECT-GROUP
        OBJECTS {
                sysConsolePrimaryLoginAuthentication,  -- deprecated
                sysConsolePrimaryEnableAuthentication, -- deprecated
                sysTelnetPrimaryLoginAuthentication,   -- deprecated
                sysTelnetPrimaryEnableAuthentication,  -- deprecated
                tacacsLoginAuthentication,             -- deprecated
                tacacsEnableAuthentication,            -- deprecated
                tacacsLocalLoginAuthentication,        -- deprecated
                tacacsLocalEnableAuthentication,       -- deprecated
                tacacsNumLoginAttempts,                -- deprecated
                tacacsDirectedRequest,
                tacacsTimeout,                         -- deprecated
                tacacsAuthKey,
                tacacsServerAddr,
                tacacsServerType,
                radiusLoginAuthentication,             -- deprecated
                radiusEnableAuthentication,            -- deprecated
                radiusDeadtime,
                radiusAuthKey,
                radiusTimeout,
                radiusRetransmits,
                radiusServerAddr,
                radiusServerAuthPort,
                radiusServerType
        }
        STATUS        deprecated
        DESCRIPTION   "A collection of objects providing information
                      about the authentication features.

                      Implementation of this group is optional. If the
                      authentication features are supported, the entire
                      group should be implemented."
        ::= { ciscoStackMIBGroups 14 }
tftpGroup OBJECT-GROUP
        OBJECTS {
                tftpHost,
                tftpFile,
                tftpModule,
                tftpAction,
                tftpResult
        }
        STATUS        current
        DESCRIPTION   "A collection of objects providing information
                      about the tftp upload/download features.

                      Implementation of this group is optional. If the
                      tftp upload/download features are supported, the
                      entire group should be implemented."
        ::= { ciscoStackMIBGroups 15 }
brouteEnableGroup OBJECT-GROUP
        OBJECTS {
                brouterPortModule,
                brouterPort,
                brouterEnableRip,
                brouterEnableSpantree,
                brouterEnableGiantCheck,
                brouterEnableIpFragmentation,
                brouterEnableUnreachables,
                brouterCamMode,
                brouterIpxSnapToEther,
                brouterIpx8023RawToFddi,
                brouterEthernetReceiveMax,
                brouterEthernetTransmitMax,
                brouterFddiReceiveMax,
                brouterFddiTransmitMax,
                brouterPortIpVlan,
                brouterPortIpAddr,
                brouterPortNetMask,
                brouterPortBroadcast,
                brouterPortBridgeVlan,
                brouterPortIpHelpers,
                brouterIpx8022ToEther,
                brouterEnableTransitEncapsulation,
                brouterEnableFddiCheck,
                brouterEnableAPaRT
        }
        STATUS        current
        DESCRIPTION   "A collection of objects providing information
                      about the combined bridging/routing feature.

                      Implementation of this group is optional. If the
                      combined bridging/routing feature is supported,
                      the group should be implemented."
        ::= { ciscoStackMIBGroups 16 }
filterGroup OBJECT-GROUP
        OBJECTS {
                filterMacModule,
                filterMacPort,
                filterMacAddress,
                filterMacType,
                filterVendorModule,
                filterVendorPort,
                filterVendorId,
                filterVendorType,
                filterProtocolModule,
                filterProtocolPort,
                filterProtocolValue,
                filterProtocolType,
                filterTestModule,
                filterTestPort,
                filterTestIndex,
                filterTestType,
                filterTestOffset,
                filterTestValue,
                filterTestMask,
                filterPortModule,
                filterPort,
                filterPortComplex,
                filterPortBroadcastThrottle,
                filterPortBroadcastThreshold,
                filterPortBroadcastDiscards
        }
        STATUS        current
        DESCRIPTION   "A collection of objects providing information
                      about the port filtering feature.

                      Implementation of this group is optional. If the
                      port filtering feature is supported, parts or all
                      of this group should be implemented."
        ::= { ciscoStackMIBGroups 17 }
monitorGroup OBJECT-GROUP
        OBJECTS {
                monitorSourceModule,
                monitorSourcePort,
                monitorDestinationModule,
                monitorDestinationPort,
                monitorDirection,
                monitorEnable,
                monitorAdminSourcePorts,
                monitorOperSourcePorts
        }
        STATUS        deprecated
        DESCRIPTION   "The collection of deprecated objects for
                       managing the Switched Port Analyzer (SPAN)
                       features."
        ::= { ciscoStackMIBGroups 18 }
vlanGroup OBJECT-GROUP
        OBJECTS {
                vlanIndex,                 -- deprecated
                vlanSpantreeEnable,        -- deprecated
                vlanIfIndex,               -- deprecated
                vlanPortModule,
                vlanPort,
                vlanPortVlan,
                vlanPortIslVlansAllowed,
                vlanPortSwitchLevel,
                vlanPortIslAdminStatus,
                vlanPortIslOperStatus,
                vlanPortIslPriorityVlans,
                vlanPortAdminStatus,
                vlanPortOperStatus
        }
        STATUS        deprecated
        DESCRIPTION   "A collection of objects providing information
                      about the Virtual LAN features.

                      Implementation of this group is optional."
        ::= { ciscoStackMIBGroups 19 }
vmpsGroup OBJECT-GROUP
        OBJECTS {
                vmpsAddr,
                vmpsType,
                vmpsAction,
                vmpsAccessed
        }
        STATUS        current
        DESCRIPTION   "A collection of objects providing information
                      about the Vlan Membership Policy Server feature.

                      Implementation of this group is optional. If the
                      Vlan Membership Policy Server feature is
                      supported, the entire group should be
                      implemented."
        ::= { ciscoStackMIBGroups 20 }
tokenRingGroup OBJECT-GROUP
        OBJECTS {
                tokenRingModuleIndex,
                tokenRingPortIndex,
                tokenRingPortSetACbits ,
                tokenRingPortMode ,
                tokenRingPortEarlyTokenRel,
                tokenRingPortPriorityThresh,
                tokenRingPortPriorityMinXmit,
                tokenRingPortCfgLossThresh,
                tokenRingPortCfgLossInterval,
                tokenRingDripDistCrfMode,
                tokenRingDripAreReductionMode,
                tokenRingDripLocalNodeID,
                tokenRingDripLastRevision,
                tokenRingDripLastChangedRevision,
                tokenRingDripAdvertsReceived,
                tokenRingDripAdvertsTransmitted,
                tokenRingDripAdvertsProcessed,
                tokenRingDripInputQueueDrops,
                tokenRingDripOutputQueueDrops,
                tokenRingDripVlan,
                tokenRingDripLocalPortStatus,
                tokenRingDripRemotePortStatus,
                tokenRingDripRemotePortConfigured,
                tokenRingDripDistributedCrf,
                tokenRingDripBackupCrf,
                tokenRingDripOwnerNodeID
        }
        STATUS        current
        DESCRIPTION   "A collection of objects providing information
                      about the token ring features.

                      Implementation of this group is optional. If the
                      token ring features are supported, the entire
                      group should be implemented."
        ::= { ciscoStackMIBGroups 21 }
mcastGroup OBJECT-GROUP
        OBJECTS {
                mcastRouterModuleIndex,
                mcastRouterPortIndex,
                mcastRouterAdminStatus,
                mcastRouterOperStatus,
                mcastEnableCgmp,
                mcastEnableIgmp
        }
        STATUS        current
        DESCRIPTION   "A collection of objects providing information
                      about the multicast features.

                      Implementation of this group is optional. If the
                      multicast features are supported, the entire group
                      should be implemented."
        ::= { ciscoStackMIBGroups 22 }
dnsGroup OBJECT-GROUP
        OBJECTS {
                dnsEnable,
                dnsServerAddr,
                dnsServerType,
                dnsDomainName
        }
        STATUS        current
        DESCRIPTION   "A collection of objects providing information
                      about the DNS feature.

                      Implementation of this group is optional. If the
                      DNS feature is supported, the entire group
                      should be implemented."
        ::= { ciscoStackMIBGroups 23 }
syslogGroup OBJECT-GROUP
        OBJECTS {
                syslogServerAddr,
                syslogServerType,
                syslogConsoleEnable,
                syslogHostEnable,
                syslogMessageFacility,
                syslogMessageSeverity,
                syslogTimeStampOption
        }
        STATUS        current
        DESCRIPTION   "A collection of objects providing information
                      about the system log feature.

                      Implementation of this group is optional. If the
                      system log feature is supported, the entire group
                      should be implemented."
        ::= { ciscoStackMIBGroups 24 }
ntpGroup OBJECT-GROUP
        OBJECTS {
                ntpBcastClient,
                ntpBcastDelay,
                ntpClient,
                ntpServerAddress,
                ntpServerType,
                ntpSummertimeStatus,
                ntpSummerTimezoneName,
                ntpTimezoneName,
                ntpTimezoneOffsetHour,
                ntpTimezoneOffsetMinute
        }
        STATUS        current
        DESCRIPTION   "A collection of objects providing information
                      about the network time protocol feature.

                      Implementation of this group is optional. If the
                      network time protocol feature is supported, the
                      entire group should be implemented."
        ::= { ciscoStackMIBGroups 25 }
ipPermitGroup OBJECT-GROUP
        OBJECTS {
                ipPermitAddress,
                ipPermitMask,
                ipPermitEnable,         -- deprecated
                ipPermitType,
                ipPermitDeniedAddress,
                ipPermitDeniedAccess,
                ipPermitDeniedTime
        }
        STATUS        deprecated
        DESCRIPTION   "A collection of objects providing information
                      about the ip permit list feature.

                      Implementation of this group is optional. If the
                      ip permit list feature is supported, the entire
                      group should be implemented."
        ::= { ciscoStackMIBGroups 26 }
mdgGatewayGroup OBJECT-GROUP
        OBJECTS {
                      mdgGatewayAddr,
                      mdgGatewayType
        }
        STATUS        current
        DESCRIPTION   "A collection of objects providing information
                      about the multiple default gateway feature.

                      Implementation of this group is optional. If the
                      multiple default gateway feature is supported,
                      the entire group should be implemented."
        ::= { ciscoStackMIBGroups 27 }
traceRouteGroup OBJECT-GROUP
        OBJECTS {
                  traceRouteMaxQueries,
                  traceRouteQueryIndex,
                  traceRouteHost,
                  traceRouteQueryDNSEnable,
                  traceRouteQueryWaitingTime,
                  traceRouteQueryInitTTL,
                  traceRouteQueryMaxTTL,
                  traceRouteQueryUDPPort,
                  traceRouteQueryPacketCount,
                  traceRouteQueryPacketSize,
                  traceRouteQueryTOS,
                  traceRouteQueryResult,
                  traceRouteQueryTime,
                  traceRouteQueryOwner,
                  traceRouteQueryStatus,
                  traceRouteDataIndex,
                  traceRouteDataGatewayName,
                  traceRouteDataGatewayIp,
                  traceRouteDataRtt,
                  traceRouteDataHopCount,
                  traceRouteDataErrors
        }
        STATUS        current
        DESCRIPTION   "A collection of objects providing information
                      about the trace route feature.

                      Implementation of this group is optional. If the
                      trace route feature is supported, the entire group
                      should be implemented."
        ::= { ciscoStackMIBGroups 28 }
deprecatedObjectGroup OBJECT-GROUP
        OBJECTS {
                      sysCommunityAccess,
                      sysCommunityString,
                      moduleHwHiVersion,
                      moduleHwLoVersion,
                      moduleFwHiVersion,
                      moduleFwLoVersion,
                      moduleSwHiVersion,
                      moduleSwLoVersion,
                      brouterCamAgingTime,
                      chassisSerialNumber,
                      moduleSerialNumber
        }
        STATUS        deprecated
        DESCRIPTION   "A collection of objects that have been
                      deprecated."
        ::= { ciscoStackMIBGroups 29 }

ntpAuthenticationGroup OBJECT-GROUP
        OBJECTS {
                ntpServerPublicKey,
                ntpAuthenticationEnable,
                ntpAuthenticationPublicKey,
                ntpAuthenticationSecretKey,
                ntpAuthenticationTrustedMode,
                ntpAuthenticationType
        }
        STATUS        current
        DESCRIPTION   "A collection of objects providing information
                      about the network time protocol authentication
                      feature.

                      Implementation of this group is optional. If the
                      network time protocol authentication feature is
                      supported, the entire group should be
                      implemented."
        ::= { ciscoStackMIBGroups 30 }

tokenRingSoftErrorMonitorGroup OBJECT-GROUP
        OBJECTS {
                tokenRingPortSoftErrThresh,
                tokenRingPortSoftErrReportInterval,
                tokenRingPortSoftErrResetCounters,
                tokenRingPortSoftErrLastCounterReset,
                tokenRingPortSoftErrEnable
        }
        STATUS        current
        DESCRIPTION   "A collection of objects providing information
                      about the token ring port soft error monitoring
                      feature.

                      Implementation of this group is optional. If the
                      token ring features are supported, the entire
                      group should be implemented."
        ::= { ciscoStackMIBGroups 31 }

portCpbGroup1        OBJECT-GROUP
        OBJECTS {
                portCpbUdld
        }
        STATUS        current
        DESCRIPTION   "A collection of objects providing additional
                      information about the port capabilities on the
                      device.

                      Implementation of this group is Optional."
        ::= { ciscoStackMIBGroups 32 }

portSecurityGroup1 OBJECT-GROUP
        OBJECTS {
                portSecurityMaxSrcAddr,
                portSecurityAgingTime,
                portSecurityShutdownTimeOut,
                portSecurityViolationPolicy,
                portSecurityExtModuleIndex,
                portSecurityExtPortIndex,
                portSecurityExtSecureSrcAddr,
                portSecurityExtControlStatus
        }
        STATUS          current
        DESCRIPTION     "A collection of objects providing additional
                        information for supporting port security feature
                        with the multiple secured source MAC addresses.
                        Implementation of this group is optional."
        ::= { ciscoStackMIBGroups 33}

fileCopyGroup OBJECT-GROUP
        OBJECTS {
                fileCopyProtocol,
                fileCopyRemoteServer,
                fileCopySrcFileName,
                fileCopyDstFileName,
                fileCopyModuleNumber,
                fileCopyUserName,
                fileCopyAction,
                fileCopyResult,
                fileCopyResultRcpErrorMessage
        }
        STATUS        current
        DESCRIPTION   "A collection of objects providing information
                      about the tftp/rcp or local file upload/download
                      features.

                      Implementation of this group is optional. If the
                      tftp upload/download features are supported, the
                      entire group should be implemented."
        ::= { ciscoStackMIBGroups 34 }

optionalSystemMiscGroup1 OBJECT-GROUP
        OBJECTS {
                sysStartupConfigSource,
                sysStartupConfigSourceFile,
                sysConfigSupervisorModuleNo,
                sysStandbyPortEnable
        }
        STATUS        current
        DESCRIPTION   "A collection of objects providing information
                      about the miscellaneous system features.

                      Implementation of this group is optional."
        ::= { ciscoStackMIBGroups 35 }

ipPermitGroup1 OBJECT-GROUP
        OBJECTS {
                ipPermitAccessType
        }
        STATUS        current
        DESCRIPTION   "A collection of objects providing additional
                      information for allowing the ip permit host with
                      the specified access type.

                      Implementation of this group is optional. If the
                      ip permit list enhancement feature is supported,
                      this group should be implemented."
        ::= { ciscoStackMIBGroups 36 }

optionalSystemMiscGroup2 OBJECT-GROUP
        OBJECTS {
                sysPortFastBpduGuard,                -- deprecated
                sysErrDisableTimeoutEnable,
                sysErrDisableTimeoutInterval,
                sysTrafficMonitorHighWaterMark,
                sysHighAvailabilityEnable,
                sysHighAvailabilityVersioningEnable,
                sysHighAvailabilityOperStatus,
                sysHighAvailabilityNotRunningReason
        }
        STATUS        deprecated
        DESCRIPTION   "A collection of objects providing information
                      about the miscellaneous system features.

                      Implementation of this group is optional."
        ::= { ciscoStackMIBGroups 37 }

filterGroup1 OBJECT-GROUP
        OBJECTS {
                filterPortBroadcastThresholdFraction
        }
        STATUS        current
        DESCRIPTION   "A collection of objects providing information
                      about the port filtering feature.

                      Implementation of this group is optional. If the
                      port filtering feature is supported, parts or all
                      of this group should be implemented."
        ::= { ciscoStackMIBGroups 38 }


mcastGroup1 OBJECT-GROUP
        OBJECTS {
                mcastEnableRgmp
        }
        STATUS        current
        DESCRIPTION   "A collection of objects providing information
                      about the multicast features.

                      Implementation of this group is optional. If the
                      multicast features are supported, the entire group
                      should be implemented."
        ::= { ciscoStackMIBGroups 39 }

portGroup1  OBJECT-GROUP
        OBJECTS {
                portAdditionalOperStatus,
                portEntPhysicalIndex
        }
        STATUS        current
        DESCRIPTION   "A collection of objects providing information
                      about the ports on the device.

                      Implementation of this group is optional."
        ::= { ciscoStackMIBGroups 40 }

chassisGroup1 OBJECT-GROUP
        OBJECTS {
                chassisPs3Type,
                chassisPs3Status,
                chassisPs3TestResult,
                chassisPEMInstalled
        }
        STATUS        current
        DESCRIPTION   "A collection of objects providing information
                      about the chassis of the device.

                      This group must be implemented by systems that can
                      have 3 or more power supplies."
        ::= { ciscoStackMIBGroups 41 }

moduleGroup1 OBJECT-GROUP
        OBJECTS {
                moduleEntPhysicalIndex
        }
        STATUS        current
        DESCRIPTION   "A collection of objects providing information
                      about the modules on the device.

                      Implementation of this group is mandatory."
        ::= { ciscoStackMIBGroups 42 }

portCpbGroup2        OBJECT-GROUP
        OBJECTS {
                portCpbSpan
        }
        STATUS        current
        DESCRIPTION   "A collection of objects providing additional
                      information about the port capabilities on the
                      device.

                      Implementation of this group is Optional."
        ::= { ciscoStackMIBGroups 43 }

voiceGroup           OBJECT-GROUP
        OBJECTS {
                voicePortIfDHCPEnabled,
                voicePortIfIpAddress,
                voicePortIfIpNetMask,
                voicePortIfTftpServerAddress,
                voicePortIfGatewayAddress,
                voicePortIfDnsServerAddress,
                voicePortIfDnsDomain,
                voicePortIfOperDnsDomain,
                voicePortCallManagerIpAddr,
                voicePortOperDnsServerIpAddr,
                voicePortOperDnsServerSource
        }
        STATUS      current
        DESCRIPTION "A collection of objects providing information
                     about the voice ports on the device.

                     Implemetation of this group is Optional"
        ::= { ciscoStackMIBGroups 44 }

portGroup2  OBJECT-GROUP
        OBJECTS {
                portInlinePowerDetect
        }
        STATUS        current
        DESCRIPTION   "A collection of objects providing information
                      about the ports on the device.

                      Implementation of this group is optional."
        ::= { ciscoStackMIBGroups 45 }

vlanGroup1 OBJECT-GROUP
        OBJECTS {
                  vlanPortAuxiliaryVlan
        }
        STATUS        deprecated
        DESCRIPTION   "A collection of objects providing information
                      about the Virtual LAN features.

                      Implementation of this group is optional. If the
                      Virtual LAN features are supported, the entire
                      group should be implemented."
        ::= { ciscoStackMIBGroups 46 }

portCpbGroup3        OBJECT-GROUP
        OBJECTS {
                portCpbInlinePower,
                portCpbAuxiliaryVlan
        }
        STATUS        current
        DESCRIPTION   "A collection of objects providing additional
                      information about the port capabilities on the
                      device.

                      Implementation of this group is Optional."
        ::= { ciscoStackMIBGroups 47 }

moduleGroup2 OBJECT-GROUP
        OBJECTS {
                moduleAdditionalStatus
        }
        STATUS        current
        DESCRIPTION   "A collection of objects providing information
                      about the modules on the device.

                      Implementation of this group is mandatory."
        ::= { ciscoStackMIBGroups 48 }

switchAccelerationModuleGroup OBJECT-GROUP
        OBJECTS {
                switchAccelerationModuleIndex,
                switchAccelerationModuleEnable
        }
        STATUS        current
        DESCRIPTION   "A collection of objects providing information
                      about the modules switch acceleration
                      configuration.

                      Implementation of this group is mandatory if the
                      module switch acceleration feature is supported."
        ::= { ciscoStackMIBGroups 49 }

optionalSystemMiscGroup3 OBJECT-GROUP
        OBJECTS {
            sysExtendedRmonNetflowModuleMask
        }
        STATUS        current
        DESCRIPTION   "A collection of objects providing information
                      about the miscellaneous system features.
                      The sysExtendedRmonNetflowModuleMask object is
                      optional object and it will only be supported in
                      the platform supporting multiple NAM (Network
                      Analysis Module) cards.
                      Implementation of this group is optional."
        ::= { ciscoStackMIBGroups 50 }

optionalSystemMiscGroup4 OBJECT-GROUP
        OBJECTS {
            sshPublicKeySize
        }
        STATUS        current
        DESCRIPTION   "A collection of objects providing information
                      about the miscellaneous system features."
        ::= { ciscoStackMIBGroups 51 }

vlanTrunkMappingGroup OBJECT-GROUP
        OBJECTS {
            vlanTrunkMappingMax,
            vlanTrunkMappingToVlan,
            vlanTrunkMappingType,
            vlanTrunkMappingOper,
            vlanTrunkMappingStatus
        }
        STATUS        current
        DESCRIPTION   "A collection of objects providing information
                      about the trunk VLAN to VLAN associations.

                      Implementation of this group is mandatory if the
                      trunk VLAN to VLAN association feature is
                      supported on the device."
        ::= { ciscoStackMIBGroups 52 }

portJumboFrameGroup OBJECT-GROUP
        OBJECTS {
            portJumboFrameModuleIndex,
            portJumboFramePortIndex,
            portJumboFrameEnable
        }
        STATUS        current
        DESCRIPTION   "A collection of objects providing information
                      about the port jumbo frame feature on the device.

                      Implementation of this group is mandatory if the
                      port jumbo frame feature is supported on the
                      device."
        ::= { ciscoStackMIBGroups 53 }

portCpbGroup4        OBJECT-GROUP
        OBJECTS {
                portCpbCosRewrite,
                portCpbTosRewrite,
                portCpbCopsGrouping
        }
        STATUS        current
        DESCRIPTION   "A collection of objects providing additional
                      information about the port capabilities on the
                      device.
                      Implementation of this group is Optional."
        ::= { ciscoStackMIBGroups 54 }

fileCopyGroup2       OBJECT-GROUP
        OBJECTS { fileCopyRuntimeConfigPart }
        STATUS        current
        DESCRIPTION   "A collection of objects providing additional
                      information about tftp/rcp or local file
                      upload/download features.

                      Implementation of this group is optional."
        ::= { ciscoStackMIBGroups 55 }

systemRmonGroup2     OBJECT-GROUP
        OBJECTS { sysMaxRmonMemory }
        STATUS        current
        DESCRIPTION "A collection of object providing RMON max memory
                     usage control."
        ::= { ciscoStackMIBGroups 56 }

filterGroup2 OBJECT-GROUP
        OBJECTS {
                filterPortSuppressionOption
        }
        STATUS        current
        DESCRIPTION   "A collection of objects providing information
                      about the unicast/multicast port filtering
                      feature."
        ::= { ciscoStackMIBGroups 57 }

optionalSystemMiscGroup5 OBJECT-GROUP
        OBJECTS { sysMacReductionAdminEnable,
                  sysMacReductionOperEnable
                }
        STATUS        current
        DESCRIPTION   "A collection of objects providing information
                      about the miscellaneous system features."
        ::= { ciscoStackMIBGroups 58 }

syslogGroup2 OBJECT-GROUP
        OBJECTS {
                syslogTelnetEnable
        }
        STATUS        current
        DESCRIPTION   "A collection of object providing control about
                      whether the syslog messages should be sent to
                      telnet sessions.

                      Implementation of this group is optional."
        ::= { ciscoStackMIBGroups 59 }

systemStatusGroup     OBJECT-GROUP
        OBJECTS { sysStatus }
        STATUS        current
        DESCRIPTION   "A collection of object providing the system
                       LED status.

                      Implementation of this group is optional."
        ::= { ciscoStackMIBGroups 60 }

configurationGroup     OBJECT-GROUP
        OBJECTS  { configMode,
                   configTextFileLocation,
                   configWriteMem,
                   configWriteMemStatus
                 }
        STATUS        current
        DESCRIPTION   "A collection of object providing the information
                      about the configuration mode to store the
                      configuration information.

                      Implementation of this group is optional."
        ::= { ciscoStackMIBGroups 61 }

filterGroup3 OBJECT-GROUP
        OBJECTS {
                filterPortSuppressionViolation
        }
        STATUS        current
        DESCRIPTION   "A collection of objects providing additional
                      information about  about the Broadcast
                      Suppression Violation for port filtering feature.

                      Implementation of this group is optional."
        ::= { ciscoStackMIBGroups 62 }

portGroup3  OBJECT-GROUP
        OBJECTS {
                portErrDisableTimeOutEnable
        }
        STATUS        current
        DESCRIPTION   "A collection of objects providing additional
                      information about the ports on the device.

                      Implementation of this group is optional."
        ::= { ciscoStackMIBGroups 63 }

portCpbGroup5  OBJECT-GROUP
        OBJECTS {
                portCpbDot1x,
                portCpbIgmpFilter
        }
        STATUS        current
        DESCRIPTION   "A collection of objects providing additional
                      information about the port capabilities on the
                      device.

                      Implementation of this group is Optional."
        ::= { ciscoStackMIBGroups 64 }

authenticationGroup1 OBJECT-GROUP
        OBJECTS {
                tacacsDirectedRequest,
                tacacsAuthKey,
                tacacsServerAddr,
                tacacsServerType,
                radiusDeadtime,
                radiusAuthKey,
                radiusTimeout,
                radiusRetransmits,
                radiusServerAddr,
                radiusServerAuthPort,
                radiusServerType
        }
        STATUS        deprecated
        DESCRIPTION   "A collection of objects providing information
                      about the authentication features.

                      Implementation of this group is optional."
        ::= { ciscoStackMIBGroups 65 }

systemMiscGroup1 OBJECT-GROUP
        OBJECTS {
                sysMgmtType,
                sysAttachType,
                sysBaudRate,
                sysInsertMode,
                sysEnableModem,
                sysEnableRedirects,
                sysArpAgingTime,
                sysCommunityRwa,
                sysCommunityRw,
                sysCommunityRo,
                sysIpVlan
        }
        STATUS        current
        DESCRIPTION   "A collection of objects providing information
                      about the miscellaneous system features."
        ::= { ciscoStackMIBGroups 66 }

systemTrapGroup1 OBJECT-GROUP
        OBJECTS {
                sysEnableChassisTraps,
                sysEnableModuleTraps,
                sysEnableBridgeTraps,
                sysEnableRepeaterTraps
        }
        STATUS        deprecated
        DESCRIPTION   "A collection of objects providing information
                      about the SNMP traps feature."
        ::= { ciscoStackMIBGroups 67 }

optionalSystemMiscGroup6 OBJECT-GROUP
        OBJECTS {
                sysErrDisableTimeoutEnable,
                sysErrDisableTimeoutInterval,
                sysTrafficMonitorHighWaterMark,
                sysHighAvailabilityEnable,
                sysHighAvailabilityVersioningEnable,
                sysHighAvailabilityOperStatus,
                sysHighAvailabilityNotRunningReason
        }
        STATUS        current
        DESCRIPTION   "A collection of objects providing information
                      about the miscellaneous system features.

                      Implementation of this group is optional."
        ::= { ciscoStackMIBGroups 68 }

optionalChassisGroup1 OBJECT-GROUP
        OBJECTS {
                chassisPs1TestResult,
                chassisPs2TestResult,
                chassisFanTestResult,
                chassisSlotConfig,
                chassisModel
        }
        STATUS        current
        DESCRIPTION   "A collection of objects providing information
                      about the chassis of the device."
        ::= { ciscoStackMIBGroups 69 }

portGroup4 OBJECT-GROUP
        OBJECTS {
                portModuleIndex,
                portIndex,
                portCrossIndex,
                portName,
                portType,
                portOperStatus,
                portCrossGroupIndex,
                portAdditionalStatus,
                portAdminSpeed,
                portDuplex,
                portIfIndex,
                portAdminRxFlowControl,
                portOperRxFlowControl,
                portAdminTxFlowControl,
                portOperTxFlowControl,
                portMacControlTransmitFrames,
                portMacControlReceiveFrames,
                portMacControlPauseTransmitFrames,
                portMacControlPauseReceiveFrames,
                portMacControlUnknownProtocolFrames,
                portLinkFaultStatus
        }
        STATUS        current
        DESCRIPTION   "A collection of objects providing information
                      about the ports on the device."
        ::= { ciscoStackMIBGroups 70 }

vlanGroup2 OBJECT-GROUP
        OBJECTS {
                vlanPortModule,
                vlanPort,
                vlanPortVlan,
                vlanPortIslVlansAllowed,
                vlanPortSwitchLevel,
                vlanPortIslAdminStatus,
                vlanPortIslOperStatus,
                vlanPortIslPriorityVlans,
                vlanPortAdminStatus,
                vlanPortOperStatus
        }
        STATUS        current
        DESCRIPTION   "A collection of objects providing information
                      about the Virtual LAN features.

                      Implementation of this group is optional."
        ::= { ciscoStackMIBGroups 71 }

ipPermitGroup2 OBJECT-GROUP
        OBJECTS {
                ipPermitAddress,
                ipPermitMask,
                ipPermitType,
                ipPermitDeniedAddress,
                ipPermitDeniedAccess,
                ipPermitDeniedTime,
                ipPermitAccessTypeEnable
        }
        STATUS        current
        DESCRIPTION   "A collection of objects providing information
                      about the ip permit list feature.

                      Implementation of this group is optional. If the
                      ip permit list feature is supported, the entire
                      group should be implemented."
        ::= { ciscoStackMIBGroups 72 }

optionalPortGroup1 OBJECT-GROUP
        OBJECTS {
                portSecurityModuleIndex,
                portSecurityPortIndex,
                portSecurityAdminStatus,
                portSecurityOperStatus,
                portSecurityLastSrcAddr,
                portSecuritySecureSrcAddr,
                portCpbModuleIndex,
                portCpbPortIndex,
                portCpbSpeed,
                portCpbDuplex,
                portCpbTrunkEncapsulationType,
                portCpbTrunkMode,
                portCpbChannel,
                portCpbBroadcastSuppression,
                portCpbFlowControl,
                portCpbSecurity,
                portCpbVlanMembership,
                portCpbPortfast,
                portTopNControlIndex,
                portTopNRateBase,
                portTopNType,
                portTopNMode,
                portTopNReportStatus,
                portTopNDuration,
                portTopNTimeRemaining,
                portTopNStartTime,
                portTopNRequestedSize,
                portTopNGrantedSize,
                portTopNOwner,
                portTopNStatus,
                portTopNIndex,
                portTopNModuleNumber,
                portTopNPortNumber,
                portTopNUtilization,
                portTopNIOOctets,
                portTopNIOPkts,
                portTopNIOBroadcast,
                portTopNIOMulticast,
                portTopNInErrors,
                portTopNBufferOverFlow
        }
        STATUS        current
        DESCRIPTION   "A collection of objects providing information
                      about the ports on the device.

                      Implementation of this group is Optional."
        ::= { ciscoStackMIBGroups 73 }

optionalSystemTrapGroup1 OBJECT-GROUP
        OBJECTS {
                sysEnableIpPermitTraps,
                sysEnableVmpsTraps,
                sysEnableConfigTraps,
                sysEnableEntityTrap
        }
        STATUS        current
        DESCRIPTION   "A collection of objects providing information
                      about the SNMP traps feature.

                      Implementation of this group is optional."
        ::= { ciscoStackMIBGroups 74 }

authenticationGroup2 OBJECT-GROUP
        OBJECTS {
                tacacsDirectedRequest,
                tacacsAuthKey,
                tacacsServerAddr,
                tacacsServerType,
                radiusDeadtime,
                radiusAuthKey,
                radiusTimeout,
                radiusRetransmits
        }
        STATUS        current
        DESCRIPTION   "A collection of objects providing information
                      about the authentication features.

                      Implementation of this group is optional."
        ::= { ciscoStackMIBGroups 75 }

systemTrapGroup2 OBJECT-GROUP
        OBJECTS {
                sysEnableChassisTraps,
                sysEnableModuleTraps,
                sysEnableRepeaterTraps
        }
        STATUS        current
        DESCRIPTION   "A collection of objects providing information
                      about the SNMP traps feature."
        ::= { ciscoStackMIBGroups 76 }

notificationGroup NOTIFICATION-GROUP
        NOTIFICATIONS {
                lerAlarmOn,
                lerAlarmOff,
                moduleUp,
                moduleDown,
                chassisAlarmOn,
                chassisAlarmOff,
                ipPermitDeniedTrap,
                sysConfigChangeTrap,
                tokenRingSoftErrExceededTrap
        }
        STATUS     current
        DESCRIPTION
            "A collection of notifications supported on the device."
        ::= { ciscoStackMIBGroups 77 }

ipPermitGroup3 OBJECT-GROUP
        OBJECTS { 
                ipPermitTelnetConnectLimit,
                ipPermitSshConnectLimit
        }
        STATUS          current
        DESCRIPTION     "A collection of objects providing configuration 
                        information on ip permit connection limit for a 
                        specific host."
        ::= { ciscoStackMIBGroups 78 }         
END
